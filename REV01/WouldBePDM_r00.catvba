Attribute VB_Name = "Begin"
'============================================================================================================================================
'********************************************************************************************************************************************
'
' TITLE: Would-be PDM (I whish a was a PDM)
' Function: Hand made PDM
' Version: 000 del 08/06/2015
' Author: Roberto Bartola robertobartola@gmail.com
'
'********************************************************************************************************************************************
'============================================================================================================================================

Public path
Public CADDIR
Public LISTAPRJtxtFile ' to delete if XML works
Public XML_File
Public LocalDir
Public PROJETTO
Public PROJETTO_TXT
Public SelectedPrj_Numeroselezionato


Sub CATMain()
'============================================================================================================================================
'********************************************************************************************************************************************
'
' Function: Run PDM
' Version: 000 del 08/06/2015
' Author: Roberto Bartola robertobartola@gmail.com
'
'********************************************************************************************************************************************
'============================================================================================================================================
'directory in cui sono la lista dei progetti e i progetti stessi
'(ovvero i file txt in cui sono ricapitolati i componenti dei progetti)
' i file di default in questa dir sono :PRJ_List.txt (l'elenco dei progetti) e i vari file dei progetti.txt
If path = "" Then
path = "C:\Users\rbartola\Documents\WORK\CAD_001"
End If
' directory in cui sono i file CAD
If LocalDir = "" Then
LocalDir = path
End If
If CADDIR = "" Then
CADDIR = "File_CAD"
End If
If LISTAPRJtxtFile = "" Then
LISTAPRJtxtFile = "PRJ_List.txt"
End If
XML_File = "C:\Users\rbartola\Documents\WORK\CAD_001\PRJList.xml"

'Inserisci nelle listbox i valori letti sul file lista progetti
Call Popola_form
     WouldBe_PDM.Show vbModeless
 '    WouldBE_DEBUG.Show vbModeless
 '    WouldBE_DEBUG.Hide
        '  UserForm1.Show vbModal
End Sub


Sub ApriDir()
'============================================================================================================================================
'********************************************************************************************************************************************
'
' Function: Open CAD directory
' Version: 000 del 08/06/2015
' Author: Roberto Bartola robertobartola@gmail.com
'
'********************************************************************************************************************************************
'============================================================================================================================================
NomeDir = CADDIR
'Nome del percorso da aprire
NomeFile = path & "\" & NomeDir & " " 'Nomecompleto
     If NomeFile = False Then
    Exit Sub
  End If
 CreateObject("WScript.Shell").Run "%SystemRoot%\explorer.exe " & """" & NomeFile & """", , True
 ' CreateObject("WScript.Shell").Run "%SystemRoot%\explorer.exe /e, /select," & """" & NomeFile & """", , True
End Sub

Sub ApriDir2()
'============================================================================================================================================
'********************************************************************************************************************************************
'
' Function: Open PRJ directory
' Version: 000 del 08/06/2015
' Author: Roberto Bartola robertobartola@gmail.com
'
'********************************************************************************************************************************************
'============================================================================================================================================

NomeDir = CADDIR
'Nome del percorso da aprire
NomeFile = path '& "\" & NomeDir & " " 'Nomecompleto
     If NomeFile = False Then
    Exit Sub
  End If
 CreateObject("WScript.Shell").Run "%SystemRoot%\explorer.exe " & """" & NomeFile & """", , True
 ' CreateObject("WScript.Shell").Run "%SystemRoot%\explorer.exe /e, /select," & """" & NomeFile & """", , True
End Sub


Sub Popola_form()
'============================================================================================================================================
'********************************************************************************************************************************************
'
' Function: Fill the list boxes with the right values (uses SUB subpopola)
' Version: 000 del 08/06/2015
' Author: Roberto Bartola robertobartola@gmail.com
'
'********************************************************************************************************************************************
'============================================================================================================================================
'File lista prj
WouldBe_PDM.ListBox1.Clear
' WouldBE_PDM.ListBox2.Clear
WouldBe_Debug.ListBox2.Clear
' WouldBE_PDM.ListBox3.Clear
WouldBe_Debug.ListBox3.Clear

CompletoFilePrjList = path & "\" & LISTAPRJtxtFile
WouldBe_PDM.ListBoxDirCur.AddItem CompletoFilePrjList
'MsgBox CompletoFilePrjList

'For i = 1 To 5
'    WouldBE_PDM.ListBox1.AddItem i
'Next
'
'WouldBE_PDM.ListBox1.AddItem "Ciao" 'str
'For i = 1 To 5
'    WouldBE_PDM.Nome_Progetto_Scelto.AddItem i
'Next

Stringa = ""

Set objFS = CreateObject("Scripting.FileSystemObject")
strFile = CompletoFilePrjList
'strFile = CATIA.FileSelectionBox("Select Text File", "*.*", 0)
Set objFile = objFS.GetFile(strFile)
Set ts = objFile.OpenAsTextStream(1, -2)
Do Until ts.AtEndOfStream
    strLine = ts.ReadLine
    ' do something with strLine
    WouldBe_PDM.ListBox1.AddItem strLine
    ' WouldBE_PDM.ListBox3.AddItem strLine & ".txt"
    WouldBe_Debug.ListBox3.AddItem strLine & ".txt"
    strLine = ts.ReadLine
    ' WouldBE_PDM.ListBox2.AddItem strLine
    WouldBe_Debug.ListBox2.AddItem strLine

        Stringa = strLine & Stringa
'    objOutFile.Write (strLine)
Loop
    WouldBe_PDM.ListBox1.Selected(SelectedPrj_Numeroselezionato) = True
ts.Close


End Sub


Sub CambiaDirectory()
'============================================================================================================================================
'********************************************************************************************************************************************
'
' Function: Changes PRJ list file
' Version: 000 del 08/06/2015
' Author: Roberto Bartola robertobartola@gmail.com
'
'********************************************************************************************************************************************
'============================================================================================================================================

Dim strFilePath As String
Dim objFile As File
Dim objTextStream As TextStream
Dim strLine As String
 
'Display file open dialog
'strFilePath = CATIA.FileSelectionBox("Select Text File", "*.txt, *.txt", 0)
'strFilePath = CATIA.FileSelectionBox("Select Text File", "*.*", 0)

'strFilePath = CATIA.FileSelectionBox("Select Text File", "PRJ_List.txt, *.*", 0)
strFilePath = CATIA.FileSelectionBox("Select PRJ_List.txt File", "*.txt", 0)

'If user clicked cancel (empty string is returned), then exit the program
If strFilePath = "" Then Exit Sub
 
'Open the file, read the first line then close the file
Set objFile = CATIA.FileSystem.GetFile(strFilePath)
'MsgBox FileSystemObject.GetFolder(objFile)
'MsgBox FileSystemObject.GetFolder()

Set objTextStream = objFile.OpenAsTextStream("ForReading")
strLine = objTextStream.ReadLine
objTextStream.Close
nome = FileSystem.Dir(strFilePath)
'MsgBox LocalDir
LocalDir = EstraiDirectory(strFilePath)
'MsgBox nome & FileSystem.GetAttr(strFilePath)
LISTAPRJtxtFile = EstraiFile(strFilePath)
'MsgBox "Totale =" & strFilePath & " DIR=" & LocalDir & "File =" & LISTAPRJtxtFile

'RB updata la lista progetti
'ExecTsvnCmd_RB "update", strFilePath
ExecTsvnCmd_RB "update", LocalDir & LISTAPRJtxtFile


'nome = FileSystem.GetAbsolutePathName(strFilePath)
'Set objFile2 = FileSystem.GetFolder(strFilePath2)
 
'Display the read text value…just to show it was read.
WouldBe_PDM.ListBoxDirCur.Clear
WouldBe_PDM.ListBoxDirCur.AddItem strFilePath

'LocalDir = EstraiDirectory (strFilePath)

'ripopola le listbox
' MsgBox "Prima di subpopola" & WouldBE_PDM.ListBoxDirCur.List(0) '& WouldBE_PDM.ListBoxDirCur.List(1)
Call Popola_sub_form

'MsgBox strFilePath
End Sub

Sub LeggiFileTxt()
'============================================================================================================================================
'********************************************************************************************************************************************
'
' Function: Read txt file
' Version: 000 del 08/06/2015
' Author: Roberto Bartola robertobartola@gmail.com
'
'********************************************************************************************************************************************
'============================================================================================================================================
Dim CATIA As Object

Selezionato = ""
PRJ = ""
FileCAD = ""
FileTxt = ""
Stringa = ""
Numeroselezionato = 0
SelectedPrj = ""
SelectedPrj_Numeroselezionato = 0

  For r = 0 To WouldBe_PDM.ListBox1.ListCount - 1
             If WouldBe_PDM.ListBox1.Selected(r) Then
              'Msg = Msg & WouldBE_PDM.ListBox1.List(r) & vbNewLine
              PRJ = WouldBe_PDM.ListBox1.List(r)
'              FileTxt = WouldBE_PDM.ListBox3.List(r)
              FileTxt = WouldBe_Debug.ListBox3.List(r)
              'FileCAD = WouldBE_PDM.ListBox2.List(r)
              FileCAD = WouldBe_Debug.ListBox2.List(r)
              SelectedPrj = WouldBe_PDM.ListBox1.List(r)
              Numeroselezionato = r
 '             SelectedPrj_Numeroselezionato = r
          End If
        
    Next r

If SelectedPrj = "" Then
MsgBox "Devi selezionare un progetto"
'End Sub
Else

'seleziona sul debug
WouldBe_Debug.ListBox2.Selected(Numeroselezionato) = True
WouldBe_Debug.ListBox3.Selected(Numeroselezionato) = True

NomefileCAD = LocalDir & "\" & CADDIR & "\" & FileCAD

 If Dir(NomefileCAD) <> "" Then
      FileExist = True
 ApriFile_RB (NomefileCAD)
      
   Else
      FileExist = False
MsgBox "Il file non esiste, eseguire il checkout"
   
   End If

'ApriFile_RB (NomefileCAD)
End If


End Sub

Sub Popola_sub_form()
'============================================================================================================================================
'********************************************************************************************************************************************
'
' Function: Fill the listboxes (called by SUB popola)
' Version: 000 del 08/06/2015
' Author: Roberto Bartola robertobartola@gmail.com
'
'********************************************************************************************************************************************
'============================================================================================================================================

'File lista prj
WouldBe_PDM.ListBox1.Clear
' WouldBE_PDM.ListBox2.Clear
WouldBe_Debug.ListBox2.Clear
' WouldBE_PDM.ListBox3.Clear
WouldBe_Debug.ListBox3.Clear

Stringa = ""
ListaUpdatafile = ""

Set objFS = CreateObject("Scripting.FileSystemObject")
'strFile = CompletoFilePrjList
strFile = WouldBe_PDM.ListBoxDirCur.List(0)
'MsgBox strFile & WouldBE_PDM.ListBoxDirCur.List(1)
'strFile = CATIA.FileSelectionBox("Select Text File", "*.*", 0)
Set objFile = objFS.GetFile(strFile)
Set ts = objFile.OpenAsTextStream(1, -2)
Do Until ts.AtEndOfStream
    strLine = ts.ReadLine
    ' do something with strLine
    WouldBe_PDM.ListBox1.AddItem strLine
    ' WouldBE_PDM.ListBox3.AddItem strLine & ".txt"
    WouldBe_Debug.ListBox3.AddItem strLine & ".txt"
     If ListaUpdatafile = "" Then
      ListaUpdatafile = strLine
     Else
     ListaUpdatafile = ListaUpdatafile & "*" & strLine
    End If
    strLine = ts.ReadLine
    ' WouldBE_PDM.ListBox2.AddItem strLine
    WouldBe_Debug.ListBox2.AddItem strLine
        Stringa = strLine & Stringa
'    objOutFile.Write (strLine)
Loop
'objOutFile.Close
ts.Close
'objFS.DeleteFile (strFile)
'objFS.MoveFile strTemp, strFile
'MsgBox "file " & Stringa

'RB updata la lista progetti
'ExecTsvnCmd_RB "update", strFilePath
ExecTsvnCmd_RB "update", ListaUpdatafile



End Sub

Sub Do_CheckOut()
'============================================================================================================================================
'********************************************************************************************************************************************
'
' Function: Does check out of the PRJ("svn update nomefile")
' Version: 000 del 08/06/2015
' Author: Roberto Bartola robertobartola@gmail.com
'
'********************************************************************************************************************************************
'============================================================================================================================================

Stringa = ""
Numeroselezionato = 0

SelectedPrj = ""
  For r = 0 To WouldBe_PDM.ListBox1.ListCount - 1
             If WouldBe_PDM.ListBox1.Selected(r) Then
              SelectedPrj = WouldBe_PDM.ListBox1.List(r)
              PROJETTO = SelectedPrj
              Numeroselezionato = r
             End If
   Next r

If SelectedPrj = "" Then
MsgBox "Devi selezionare un progetto"
'End Sub
Else
'seleziona sul debug
WouldBe_Debug.ListBox2.Selected(Numeroselezionato) = True
WouldBe_Debug.ListBox3.Selected(Numeroselezionato) = True

'FileTxt = WouldBE_PDM.ListBox3.List(Numeroselezionato)
FileTxt = WouldBe_Debug.ListBox3.List(Numeroselezionato)
'MsgBox "Selezionato il file txt:" & FileTxt
Set objFS = CreateObject("Scripting.FileSystemObject")
strFile = LocalDir & "\" & FileTxt
PROJETTO_TXT = strFile
'MsgBox strFile 'il nome completo del file txt con tutti i file cad
Set objFile = objFS.GetFile(strFile)
Set ts = objFile.OpenAsTextStream(1, -2)
Do Until ts.AtEndOfStream
    strLine = ts.ReadLine
FileToCommitare = LocalDir & "\" & CADDIR & "\" & strLine
    ' do something with strLine
       If Stringa <> "" Then
                Stringa = FileToCommitare & "*" & Stringa
            Else: Stringa = FileToCommitare
    End If
    
'        Stringa = strLine & Stringa
'    objOutFile.Write (strLine)
Loop
'objOutFile.Close
ts.Close

ExecTsvnCmd_RB "update", Stringa
End If
End Sub


Function EstraiDirectory(Percorso)
'============================================================================================================================================
'********************************************************************************************************************************************
'
' Function: Extracts dir name from fullname
' Version: 000 del 08/06/2015
' Author: Roberto Bartola robertobartola@gmail.com
'
'********************************************************************************************************************************************
'============================================================================================================================================
EstraiDirectory = Left(Percorso, Len(Percorso) - Len(Right(Percorso, Len(Percorso) - InStrRev(Percorso, "\"))) - 1)
End Function

Function EstraiFile(Percorso)
'============================================================================================================================================
'********************************************************************************************************************************************
'
' Function: Extracts the filename from fullname
' Version: 000 del 08/06/2015
' Author: Roberto Bartola robertobartola@gmail.com
'
'********************************************************************************************************************************************
'============================================================================================================================================
EstraiFile = Right(Percorso, Len(Percorso) - InStrRev(Percorso, "\"))
End Function

Function ApriFile_RB(nome)
'============================================================================================================================================
'********************************************************************************************************************************************
'
' Function: Open the file
' Version: 000 del 08/06/2015
' Author: Roberto Bartola robertobartola@gmail.com
'
'********************************************************************************************************************************************
'============================================================================================================================================

Dim FileName As String
Dim documents1 As Documents
Dim Document1 As Document
FileName = nome
' open the drawing that contains the titleblock that we want
'MsgBox "Nome del file " & FileName
Set documents1 = CATIA.Documents
Set Document1 = documents1.Open(FileName)

'CATIA.Documents.Open(FileName)
'CATIA.Documents.Read()
'CATIA.Documents.Read
End Function

'Aggiungi file CAD al progetto
Sub AggiungiFileCADalPRJ()
'============================================================================================================================================
'********************************************************************************************************************************************
'
' Funzione: aggiunge il file CAD attivo al PRJ.txt selezionato
' Versione: 000 del 08/06/2015
' Autore Roberto Bartola robertobartola@gmail.com
'
'********************************************************************************************************************************************
'============================================================================================================================================

Set Document = CATIA.ActiveDocument
Set objFS = CreateObject("Scripting.FileSystemObject")
Lista_progetti = 0

DocFullName = Document.FullName

DocNoFullName = EstraiFile(Document.FullName)

'directory in cui sono i progetti
'faccio pulizia, commento qui sotto dovro cancellare
'If path = "" Then
'path = "C:\Users\rbartola\Documents\WORK\CAD_001"
'End If
'' directory in cui sono i file CAD
'If LocalDir = "" Then
'LocalDir = path
'End If
'If CADDIR = "" Then
'CADDIR = "File_CAD"
'End If
'If LISTAPRJtxtFile = "" Then
'LISTAPRJtxtFile = "PRJ_List.txt"
'End If
'endcommento

Numeroselezionato = 0
SelectedPrj = ""
  For r = 0 To WouldBe_PDM.ListBox1.ListCount - 1
             If WouldBe_PDM.ListBox1.Selected(r) Then
              SelectedPrj = WouldBe_PDM.ListBox1.List(r)
              PROJETTO = SelectedPrj
              Numeroselezionato = r
             End If
   Next r
   
   'seleziona sul debug
WouldBe_Debug.ListBox2.Selected(Numeroselezionato) = True
WouldBe_Debug.ListBox3.Selected(Numeroselezionato) = True

'FileTxt = WouldBE_PDM.ListBox3.List(Numeroselezionato)
FileTxt = WouldBe_Debug.ListBox3.List(Numeroselezionato)
'MsgBox "Selezionato il file txt:" & FileTxt
Set objFS = CreateObject("Scripting.FileSystemObject")
strFile = LocalDir & "\" & FileTxt
PROJETTO_TXT = strFile

'Call Popola_form
'     WouldBE_PDM.Show vbModeless
        '  Use
    '    rForm1.Show vbModal
'MsgBox "Aggiungi il file nel progetto: " & LISTAPRJtxtFile
'fie del progetto in cui aggiungere un fileCAD
'MsgBox "Vorrei aggiungere il file " & DocNoFullName & " al progetto: " & PROJETTO_TXT
Dimmi = MsgBox("Vuoi aggiungere il file " & DocNoFullName & " al progetto: " & PROJETTO & " ?", vbYesNo, "Write confirm")
If Dimmi = vbYes Then

'strFile = CompletoFilePrjList

Open PROJETTO_TXT For Input As #1

While EOF(1) = False
    'read the current line of text
    Line Input #1, strLine
    'add the current line to strData
    strData = strData & strLine & vbCrLf
'MsgBox strData
Wend
strData = strData + DocNoFullName
Close #1
Open PROJETTO_TXT For Output As #1
Print #1, strData
Close #1

End If

End Sub

Sub ControllaFileCadQualePRJ()
'============================================================================================================================================
'********************************************************************************************************************************************
'
' Function: Search the PRJ.txt where is used current file
' Version: 000 del 08/06/2015
' Author: Roberto Bartola robertobartola@gmail.com
'
'********************************************************************************************************************************************
'============================================================================================================================================

WouldBe_PDM.Lista_projetti_coinvolti.Clear

For n = 0 To CATIA.Documents.Count
Next n

If n = 1 Then
MsgBox "Devi avere un file CATIA attivo"
Exit Sub
End If
'MsgBox N

'If CATIA.ActiveDocument Then ' prova ma non va
Set Document = CATIA.ActiveDocument
'Else: Exit Sub 'vedi sopra
'End If ' vedi sopra

DocFullName = Document.FullName
DocNoFullName = EstraiFile(Document.FullName)
Set objFS = CreateObject("Scripting.FileSystemObject")

'directory in cui sono i progetti
Lista_progetti = 0

'anche qui eliminotutto
'' leggi i valori selezionati e file cad selezionato
'If path = "" Then
'path = "C:\Users\rbartola\Documents\WORK\CAD_001"
'End If
'' directory in cui sono i file CAD
'If LocalDir = "" Then
'LocalDir = path
'End If
'If CADDIR = "" Then
'CADDIR = "File_CAD"
'End If
'If LISTAPRJtxtFile = "" Then
'LISTAPRJtxtFile = "PRJ_List.txt"
'End If
'eliminofinoqui


Set objFS = CreateObject("Scripting.FileSystemObject")
strFile = LocalDir & "\" & FileTxt
PROJETTO_TXT = strFile

'inizia controllo


'Dimmi = MsgBox("Verifica presenza del file " & DocNoFullName & " ai " & WouldBE_PDM.ListBox1.ListCount & " progetti: " & " ?", vbYesNo, "Write confirm")
'If Dimmi = vbYes Then

  For r = 0 To WouldBe_PDM.ListBox1.ListCount - 1
   '            ProjettoTot = ProjettoTot & " " & WouldBE_PDM.ListBox1.List(r) & ".txt"
   
'   PROJETTO_TXT = LocalDir & "\" & WouldBE_PDM.ListBox3.List(r)
   PROJETTO_TXT = LocalDir & "\" & WouldBe_Debug.ListBox3.List(r)
   
   
Set objFile = objFS.GetFile(PROJETTO_TXT)
Set ts = objFile.OpenAsTextStream(1, -2)
Do Until ts.AtEndOfStream
    strLine = ts.ReadLine
    ' do something with strLine
If strLine = DocNoFullName Then
Lista_progetti = Lista_progetti + 1
'WouldBE_PDM.Lista_projetti_coinvolti.AddItem Left(WouldBE_PDM.ListBox3.List(r), Len(WouldBE_PDM.ListBox3.List(r)) - 4) 'Lista il progetto (senza txt)
WouldBe_PDM.Lista_projetti_coinvolti.AddItem Left(WouldBe_Debug.ListBox3.List(r), Len(WouldBe_Debug.ListBox3.List(r)) - 4) 'Lista il progetto (senza txt)
'WouldBE_PDM.Lista_projetti_coinvolti.AddItem WouldBE_PDM.ListBox3.List(r) 'Lista il nomefile progetto (.txt)
End If
'    objOutFile.Write (strLine)
Loop
'objOutFile.Close
ts.Close
 
   
   
   Next r
 '  End If

End Sub

Sub MostraNascondiDebug()
'============================================================================================================================================
'********************************************************************************************************************************************
'
' Function: show/noshow debug form
' Version: 000 del 08/06/2015
' Author: Roberto Bartola robertobartola@gmail.com
'
'********************************************************************************************************************************************
'============================================================================================================================================

'MsgBox WouldBE_PDM.ListBox2.Visible
If WouldBe_Debug.Visible = True Then
'If WouldBE_PDM.ListBox2.Visible = True Then
'WouldBE_PDM.ListBox2.Visible = False
'WouldBE_PDM.ListBox3.Visible = False
WouldBe_Debug.Hide
Exit Sub
End If
If WouldBe_Debug.Visible = False Then
'If WouldBE_PDM.ListBox2.Visible = False Then
'WouldBE_PDM.ListBox2.Visible = True
'WouldBE_PDM.ListBox3.Visible = True
WouldBe_Debug.Show vbModeless
Exit Sub
End If
End Sub


Sub DoShowLog()
'============================================================================================================================================
'********************************************************************************************************************************************
'
' Function: Show log  of PRJ ("svn log nomefile")
' Version: 000 del 08/06/2015
' Author: Roberto Bartola robertobartola@gmail.com
'
'********************************************************************************************************************************************
'============================================================================================================================================
Stringa = ""
Numeroselezionato = 0

SelectedPrj = ""
  For r = 0 To WouldBe_PDM.ListBox1.ListCount - 1
             If WouldBe_PDM.ListBox1.Selected(r) Then
              SelectedPrj = WouldBe_PDM.ListBox1.List(r)
              PROJETTO = SelectedPrj
              Numeroselezionato = r
             End If
   Next r

If SelectedPrj = "" Then
MsgBox "Devi selezionare un progetto"
'End Sub
Else
'seleziona sul debug
WouldBe_Debug.ListBox2.Selected(Numeroselezionato) = True
WouldBe_Debug.ListBox3.Selected(Numeroselezionato) = True

'FileTxt = WouldBE_PDM.ListBox3.List(Numeroselezionato)
FileTxt = WouldBe_Debug.ListBox3.List(Numeroselezionato)
'MsgBox "Selezionato il file txt:" & FileTxt
Set objFS = CreateObject("Scripting.FileSystemObject")
strFile = LocalDir & "\" & FileTxt
PROJETTO_TXT = strFile
'MsgBox strFile 'il nome completo del file txt con tutti i file cad
Set objFile = objFS.GetFile(strFile)
Set ts = objFile.OpenAsTextStream(1, -2)
Do Until ts.AtEndOfStream
    strLine = ts.ReadLine
FileToCommitare = LocalDir & "\" & CADDIR & "\" & strLine
    ' do something with strLine
       If Stringa <> "" Then
                Stringa = FileToCommitare & "*" & Stringa
            Else: Stringa = FileToCommitare
    End If
    
'        Stringa = strLine & Stringa
'    objOutFile.Write (strLine)
Loop
'objOutFile.Close
ts.Close
ExecTsvnCmd_RB "log", Stringa
End If
 
End Sub

Attribute VB_Name = "BottomUpCreate"
Sub Dir_current_RB_go()
'popola la lista con la dir corrente cad
'directory in cui sono i progetti -----------------------------------Funziona  !!!!!!!!!!!!!!!!


'provo ad eliminare tutti riferimenti al path
'If path = "" Then
'path = "C:\Users\rbartola\Documents\WORK\CAD_001"
'End If
'' directory in cui sono i file CAD
'If LocalDir = "" Then
'LocalDir = path
'End If
'If CADDIR = "" Then
'CADDIR = "File_CAD"
'End If
'fino qui

LocaldirectoryDaListare = LocalDir & "\" & CADDIR
'MsgBox LocaldirectoryDaListare
WouldBe_Debug.CheckFigli1.Clear
file_name = Dir$(LocaldirectoryDaListare & "\*.*", vbDirectory)
'file_name = Dir$(strDrive & "\*.*", vbDirectory)
'directory in cui sono i progetti -----------------------------------Funziona  !!!!!!!!!!!!!!!!
For i = 1 To 100
 file_name = Dir$()
    If Len(file_name) = 0 Then Exit For
     If Not (Left(file_name, 2) = "..") Then
     'verifica sia catpart o catproduct o catdrawing
     If Right(file_name, 7) = "CATPart" Then WouldBe_Debug.CheckFigli1.AddItem file_name
     If Right(file_name, 10) = "CATProduct" Then WouldBe_Debug.CheckFigli1.AddItem file_name
     If Right(file_name, 10) = "CATDrawing" Then WouldBe_Debug.CheckFigli1.AddItem file_name
     'WouldBE_DEBUG.CheckFigli1.AddItem file_name
'          WouldBE_DEBUG.CheckFigli1.AddItem i & "-" & Len(file_name) & "-" & file_name
     End If
Next i

End Sub


Sub Check_bottomUp_go()
' Set the CATIA popup file alerts to False
CATIA.DisplayFileAlerts = False
' oppure metto in read invece che open

WouldBe_Debug.File_analizzato_name.Clear
WouldBe_PDM.Lista_Bottom_up.Clear
WouldBe_Debug.Cercato_file_OUT.Caption = ""

'provo ad eliminare tutti riferimenti al path
'If path = "" Then
'path = "C:\Users\rbartola\Documents\WORK\CAD_001"
'End If
'' directory in cui sono i file CAD
'If LocalDir = "" Then
'LocalDir = path
'End If
'If CADDIR = "" Then
'CADDIR = "File_CAD"
'End If
'fino qui

'LocaldirectoryRB = LocalDir & "\" & CADDIR
 '    Debug.Print CATIA.ActiveDocument.FullName
 '   Call AnalyseSubProduct(oStiDBItem, CATIA.ActiveDocument.FullName, "")
'MsgBox CATIA.ActiveDocument.FullName



filadalavorare = EstraiFile(CATIA.ActiveDocument.FullName)
WouldBe_Debug.File_analizzato_name.AddItem filadalavorare
WouldBe_PDM.Lista_Bottom_up.AddItem filadalavorare
WouldBe_Debug.Cercato_file_OUT.Caption = filadalavorare

FileDaRiaprireAllaFine = CATIA.ActiveDocument.FullName
'commenta per non vedere
'If WouldBE_DEBUG.Visible = False Then WouldBE_DEBUG.Show vbModeless
Call Dir_current_RB_go
'WouldBE_DEBUG.CheckFigli1.Clear
WouldBe_Debug.CheckFigli2.Clear
WouldBe_Debug.CheckFigli3.Clear
WouldBe_Debug.CheckFigli4.Clear
WouldBe_Debug.CheckFigli2.AddItem filadalavorare

'Prova loop - rb001
Numero_giri = 0

LoopRB:
Numero_file_aggiunti = 0
Numero_giri = Numero_giri + 1

Call Check_bottomUp_loop
 
WouldBe_Debug.CheckFigli5.Clear
For i = 0 To WouldBe_Debug.CheckFigli1.ListCount - 1
WouldBe_Debug.CheckFigli5.AddItem WouldBe_Debug.CheckFigli1.List(i)
Next i
WouldBe_Debug.CheckFigli1.Clear
WouldBe_Debug.CheckFigli2.Clear
For i = 0 To WouldBe_Debug.CheckFigli3.ListCount - 1
WouldBe_Debug.CheckFigli2.AddItem WouldBe_Debug.CheckFigli3.List(i)
'anchetrovati File_analizzato_name
WouldBe_Debug.File_analizzato_name.AddItem WouldBe_Debug.CheckFigli3.List(i)
WouldBe_PDM.Lista_Bottom_up.AddItem WouldBe_Debug.CheckFigli3.List(i)
Numero_file_aggiunti = Numero_file_aggiunti + 1
Next i
WouldBe_Debug.CheckFigli3.Clear
For i = 0 To WouldBe_Debug.CheckFigli5.ListCount - 1
Trovato = 0
For j = 0 To WouldBe_Debug.CheckFigli2.ListCount - 1
If WouldBe_Debug.CheckFigli5.List(i) = WouldBe_Debug.CheckFigli2.List(j) Then Trovato = 1
Next j
If Trovato = 0 Then WouldBe_Debug.CheckFigli1.AddItem WouldBe_Debug.CheckFigli5.List(i)
Next i
WouldBe_Debug.CheckFigli5.Clear

'ora devo loopare tutto
If WouldBe_Debug.CheckFigli1.ListCount = 0 Or WouldBe_Debug.CheckFigli2.ListCount = 0 Or Numero_file_aggiunti = 0 Then
MsgBox "Concluso il loop Numero giri=" & Numero_giri & " file aggiunti questo giro: " & Numero_file_aggiunti
GoTo endloop
End If
'--------------------------devi mettere la richiesta nuovo loop
Dimmi = MsgBox("Vuoi fare un nuovo giro? Numero giri=" & Numero_giri & " file aggiunti questo giro: " & Numero_file_aggiunti & " ?", vbYesNo, "Write confirm")
If Dimmi = vbYes Then GoTo LoopRB

 
endloop:

'tutto finito, riapri il documento iniziale
CATIA.Documents.Open (FileDaRiaprireAllaFine)
CATIA.DisplayFileAlerts = True

'provo a subappaltare
'  For r = 0 To WouldBE_DEBUG.CheckFigli1.ListCount - 1
'DocFullName_RB = LocaldirectoryRB & "\" & WouldBE_DEBUG.CheckFigli1.List(r)
''MsgBox DocFullName_RB
''CATIA.Documents.Open DocFullName_RB
'CATIA.Documents.Open (DocFullName_RB)
'Call AnalyseLink
'CATIA.ActiveDocument.Close'
'
'For j = 0 To WouldBE_DEBUG.CheckFigli2.ListCount - 1
'For k = 0 To WouldBE_DEBUG.CheckFigli4.ListCount - 1
'If WouldBE_DEBUG.CheckFigli4.List(k) = WouldBE_DEBUG.CheckFigli2.List(j) Then
''For l = 0 To WouldBE_DEBUG.CheckFigli3.ListCount - 1
''If WouldBE_DEBUG.CheckFigli2.List(j) <> WouldBE_DEBUG.CheckFigli3.List(l) Then WouldBE_DEBUG.CheckFigli3.AddItem WouldBE_DEBUG.CheckFigli2.List(j)
'WouldBE_DEBUG.CheckFigli3.AddItem WouldBE_DEBUG.CheckFigli1.List(r)
''Next l
'End If
'
'Next k
'Next j
'
''Set oStiDBItem = oStiEngine.GetStiDBItemFromAnyObject(CATIA.ActiveDocument)
'
'
''                'Open the drawing and get at the root parameters
''                Set objDwgDoc = CATIA.Documents.Open(objFile.Path)
''                Set objParams = objDwgDoc.Parameters.RootParameterSet.AllParameters
'
'
''poi anra bene
'  'Call AnalyseSubProduct(oStiDBItem, CATIA.ActiveDocument.FullName, "")
''Call AnalyseSubProduct(oStiDBItem, CATIA.ActiveDocument.FullName, "")
'WouldBE_DEBUG.CheckFigli4.Clear
'
'Next r
'
'WouldBE_DEBUG.CheckFigli5.Clear
'For i = 0 To WouldBE_DEBUG.CheckFigli1.ListCount - 1
'For j = 0 To WouldBE_DEBUG.CheckFigli2.ListCount - 1
'If WouldBE_DEBUG.CheckFigli1.List(i) <> WouldBE_DEBUG.CheckFigli2.List(j) Then WouldBE_DEBUG.CheckFigli5.AddItem WouldBE_DEBUG.CheckFigli1.List(i)
'Next j
'Next i
'
'WouldBE_DEBUG.CheckFigli1.Clear
'For i = 0 To WouldBE_DEBUG.CheckFigli5.ListCount - 1
'WouldBE_DEBUG.CheckFigli1.AddItem WouldBE_DEBUG.CheckFigli5.List(i)
'Next i
'WouldBE_DEBUG.CheckFigli5.Clear
'
'eliminare tutto fino a qui
'spostato in alto
'CATIA.Documents.Open (FileDaRiaprireAllaFine)
End Sub

'provo ad eliminare tutti riferimenti al path

'Sub Check_bottomUp_gobbbbbho()
' Dim objFolder As Object
'    Dim intIndex As Integer
'    Dim intIndex2 As Integer
'    Dim objFile As File
'    Dim objDwgDoc As Document
'    Dim objParams As Parameters
'    Dim strParamName As String
'    Dim varParamNames As Variant
'    Dim strOutputValues As String
'    Dim intArraySize As Integer
'    Dim strOutputFilePath As String
'    Dim objTextStream As TextStream
'    Dim strOutput As String
'    Dim objFileSystem As Object
'    Dim strTimeStamp As String
'    Dim lngNbDwgs As Long
'Set StiEngine = CATIA.GetItem("CAIEngine")
'
'    Const FOLDER As String = "C:\Users\rbartola\Documents\WORK\CAD_001\File_CAD"
'
'
'      Dim oStiEngine ' As StiEngine
'    Set oStiEngine = CATIA.GetItem("CAIEngine")
'    Dim oStiDBItem ' As StiDBItem
''    Set oStiDBItem = oStiEngine.GetStiDBItemFromAnyObject(CATIA.ActiveDocument)
'
'
'If path = "" Then
'path = "C:\Users\rbartola\Documents\WORK\CAD_001"
'End If
'' directory in cui sono i file CAD
'If LocalDir = "" Then
'LocalDir = path
'End If
'If CADDIR = "" Then
'CADDIR = "File_CAD"
'End If
'LocaldirectoryRB = LocalDir & "\" & CADDIR
' '    Debug.Print CATIA.ActiveDocument.FullName
' '   Call AnalyseSubProduct(oStiDBItem, CATIA.ActiveDocument.FullName, "")
''MsgBox CATIA.ActiveDocument.FullName
'filadalavorare = EstraiFile(CATIA.ActiveDocument.FullName)
'
''commenta per non vedere
''If WouldBE_DEBUG.Visible = False Then WouldBE_DEBUG.Show vbModeless
'Call Dir_current_RB_go
''WouldBE_DEBUG.CheckFigli1.Clear
'WouldBE_DEBUG.CheckFigli2.Clear
'WouldBE_DEBUG.CheckFigli3.Clear
'WouldBE_DEBUG.CheckFigli4.Clear
'
'WouldBE_DEBUG.CheckFigli2.AddItem filadalavorare
'
'  For r = 0 To WouldBE_DEBUG.CheckFigli1.ListCount - 1
'DocFullName_RB = LocaldirectoryRB & "\" & WouldBE_DEBUG.CheckFigli1.List(r)
'MsgBox DocFullName_RB
'
''CATIA.Documents.Open DocFullName_RB
'CATIA.Documents.Open (DocFullName_RB)
' Set oStiDBItem = oStiEngine.GetStiDBItemFromAnyObject(CATIA.ActiveDocument)
'
'
''                'Open the drawing and get at the root parameters
''                Set objDwgDoc = CATIA.Documents.Open(objFile.Path)
''                Set objParams = objDwgDoc.Parameters.RootParameterSet.AllParameters
'
'
''poi anra bene
'  'Call AnalyseSubProduct(oStiDBItem, CATIA.ActiveDocument.FullName, "")
'Call AnalyseSubProduct_RB2(oStiDBItem, CATIA.ActiveDocument.FullName, "")
'
'
'''''''''''''''''
'                'Append the drawing name to the output string
'                strOutput = strOutput & lngNbDwgs & Chr(9)
'                strOutput = strOutput & objDwgDoc.Name & Chr(9)
'
'                'Get the value of each requested parameter and
'                'append them to the output string
'                For intIndex2 = 0 To intArraySize
'                    strParamName = Trim(varParamNames(intIndex2))
'                    strOutput = strOutput & Chr(9) & GetParameterValue(objParams, strParamName)
'                Next
'                strOutput = strOutput & Chr(13)
'
'                'Close the drawing
'              DocFullName_RB.CATIA.Documents.Close
 'CATIA.Documents.Close (DocFullName_RB)
'              objDwgDoc.Close
'
'            End If

'  Call AnalyseSubProduct(oStiDBItem, CATIA.ActiveDocument.FullName, "")
              
              
 '             FileCAD = WouldBE_DEBUG.ListBox2.List(r)
 '             SelectedPrj = WouldBE_PDM.ListBox1.List(r)
 '             Numeroselezionato = r
 '             SelectedPrj_Numeroselezionato = r
'  Next r

'End Sub



Sub AnalyseSubProduct_RB2(oStiDBItem, FatherName As String, TabStrFather As String)
'If WouldBE_DEBUG.Visible = False Then WouldBE_DEBUG.Show vbModeless



    Dim i As Integer
    Dim oStiDBChildren
    Dim oStiDBItem2 ' As StiDBItem  -- Smarteam is not SetUp , API recognize , so use AnyObject Type
    Dim SonName As String
    Dim TabStrChildren As String
   
    Set oStiDBChildren = oStiDBItem.GetChildren
    For i = 1 To oStiDBChildren.Count
        Set oStiDBItem2 = oStiDBChildren.Item(i)
        SonName = oStiDBItem2.GetDocumentFullPath
        SonNameSolo = EstraiFile(SonName) ' oStiDBItem2.Name ' come si da il nome da solo? 'DocumentoAttuale = CATIA.ActiveDocument.Name
        
        TabStrChildren = TabStrFather & "-"
        LinkType = CStr(oStiDBChildren.LinkType(i))
        If SonName = FatherName Then
            ' in Case of Product with Subcompoent   Or Product with CATIA V4 model
            ' recursive Analyse to SubProduct
            Call AnalyseSubProduct_RB2(oStiDBItem2, FatherName, TabStrChildren)
        Else
            ' Add information in Database about link between Files
            Debug.Print TabStrFather & SonName & "  " & i & "" & oStiDBChildren.Count & "  " & LinkType
            'MsgBox TabStrFather & SonName & "  " & i & "" & oStiDBChildren.Count & "  " & LinkType
            MsgBox SonNameSolo
            
        End If
    Next i

End Sub



Sub Check_bottomUp_loop()
'WouldBE_DEBUG.File_analizzato_name.Clear
'WouldBE_DEBUG.Cercato_file_OUT.Caption = ""

'If Path = "" Then
'Path = "C:\Users\rbartola\Documents\WORK\CAD_001"
'End If
'' directory in cui sono i file CAD
'If LocalDir = "" Then
'LocalDir = Path
'End If
'If CADDIR = "" Then
'CADDIR = "File_CAD"
'End If
LocaldirectoryRB = LocalDir & "\" & CADDIR
 '    Debug.Print CATIA.ActiveDocument.FullName
 '   Call AnalyseSubProduct(oStiDBItem, CATIA.ActiveDocument.FullName, "")
'MsgBox CATIA.ActiveDocument.FullName
'filadalavorare = EstraiFile(CATIA.ActiveDocument.FullName)
'WouldBE_DEBUG.File_analizzato_name.AddItem filadalavorare
'WouldBE_DEBUG.Cercato_file_OUT.Caption = filadalavorare
'
'FileDaRiaprireAllaFine = CATIA.ActiveDocument.FullName
'commenta per non vedere
'If WouldBE_DEBUG.Visible = False Then WouldBE_DEBUG.Show vbModeless
'Call Dir_current_RB_go
'WouldBE_DEBUG.CheckFigli1.Clear
'WouldBE_DEBUG.CheckFigli2.Clear
'WouldBE_DEBUG.CheckFigli3.Clear
'WouldBE_DEBUG.CheckFigli4.Clear
'WouldBE_DEBUG.CheckFigli2.AddItem filadalavorare

  For r = 0 To WouldBe_Debug.CheckFigli1.ListCount - 1
DocFullName_RB = LocaldirectoryRB & "\" & WouldBe_Debug.CheckFigli1.List(r)
'MsgBox DocFullName_RB
'CATIA.Documents.Open DocFullName_RB
CATIA.Documents.Open (DocFullName_RB)
Call AnalyseLink
CATIA.ActiveDocument.Close

For j = 0 To WouldBe_Debug.CheckFigli2.ListCount - 1
For k = 0 To WouldBe_Debug.CheckFigli4.ListCount - 1
If WouldBe_Debug.CheckFigli4.List(k) = WouldBe_Debug.CheckFigli2.List(j) Then
'For l = 0 To WouldBE_DEBUG.CheckFigli3.ListCount - 1
'If WouldBE_DEBUG.CheckFigli2.List(j) <> WouldBE_DEBUG.CheckFigli3.List(l) Then WouldBE_DEBUG.CheckFigli3.AddItem WouldBE_DEBUG.CheckFigli2.List(j)
WouldBe_Debug.CheckFigli3.AddItem WouldBe_Debug.CheckFigli1.List(r)
'Next l
End If

Next k
Next j

'Set oStiDBItem = oStiEngine.GetStiDBItemFromAnyObject(CATIA.ActiveDocument)


'                'Open the drawing and get at the root parameters
'                Set objDwgDoc = CATIA.Documents.Open(objFile.Path)
'                Set objParams = objDwgDoc.Parameters.RootParameterSet.AllParameters
  
  
'poi anra bene
  'Call AnalyseSubProduct(oStiDBItem, CATIA.ActiveDocument.FullName, "")
'Call AnalyseSubProduct(oStiDBItem, CATIA.ActiveDocument.FullName, "")
WouldBe_Debug.CheckFigli4.Clear

Next r

WouldBe_Debug.CheckFigli5.Clear
For i = 0 To WouldBe_Debug.CheckFigli1.ListCount - 1
Nocambiato = 0
For j = 0 To WouldBe_Debug.CheckFigli2.ListCount - 1
If WouldBe_Debug.CheckFigli1.List(i) <> WouldBe_Debug.CheckFigli2.List(j) And Nocambiato = 0 Then
Nocambiato = 1
WouldBe_Debug.CheckFigli5.AddItem WouldBe_Debug.CheckFigli1.List(i)
End If
Next j
Next i

WouldBe_Debug.CheckFigli1.Clear
For i = 0 To WouldBe_Debug.CheckFigli5.ListCount - 1
WouldBe_Debug.CheckFigli1.AddItem WouldBe_Debug.CheckFigli5.List(i)
Next i
WouldBe_Debug.CheckFigli5.Clear

'CATIA.Documents.Open (FileDaRiaprireAllaFine)


End Sub

Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public Property Get ss() As Variant
Import win32com.client
catapp = win32com.client.Dispatch("CATIA.Application")
Doc = catapp.ActiveDocument.Product
 
product_count = Doc.Products.Count
Print "This example lists all Parts and Subproducts of the first level from a CATProduct."
for products in range(product_count):
Products = Products + 1
Print Doc.Products.Item(Products).Name, ":"
part_count = Doc.Products.Item(Products).Products.Count
for parts in range(part_count):
parts = parts + 1
Print " ", Doc.Products.Item(Products).Products.Item(parts).Name
End Property

Public Property Let ss(ByVal vNewValue As Variant)

End Property

Attribute VB_Name = "Out_module"
Sub GO_Esporta_su_File()

Dim strFilePath As String
strFilePath = CATIA.FileSelectionBox("SaveAs", "*.txt", 1)
If strFilePath = "" Then
   strMsg = "File selection was cancelled, so the program will end."
   MsgBox strMsg, 64, "Program End"
   Exit Sub
End If
If Right(strFilePath, 4) <> ".txt" Then strFilePath = strFilePath & ".txt"

Open strFilePath For Output As #1
MsgBox "Nome File:" & strFilePath
For i = 0 To WouldBe_PDM.Lista_Bottom_up.ListCount - 1
'For i = 0 To WouldBE_DEBUG.File_analizzato_name.ListCount - 1 'alternativo
'Write #1, Left(Right(WouldBE_DEBUG.File_analizzato_name.List(i), Len(WouldBE_DEBUG.File_analizzato_name.List(i)) - 1), Len(WouldBE_DEBUG.File_analizzato_name.List(i)) - 2)
'Print #1, WouldBE_DEBUG.File_analizzato_name.List(i) ' opzione
Print #1, WouldBe_PDM.Lista_Bottom_up.List(i)
Next i
Close #1


End Sub


Sub GO_Esporta_su_File_PRJ()

Dim strFilePath As String
strFilePath = CATIA.FileSelectionBox("SaveAs", "*.txt", 1)
If strFilePath = "" Then
   strMsg = "File selection was cancelled, so the program will end."
   MsgBox strMsg, 64, "Program End"
   Exit Sub
End If
If Right(strFilePath, 4) <> ".txt" Then strFilePath = strFilePath & ".txt"

Open strFilePath For Output As #1
MsgBox "Nome File:" & strFilePath
For i = 0 To WouldBe_PDM.Lista_TOP_DOWN.ListCount - 1
'For i = 0 To WouldBE_DEBUG.File_analizzato_name.ListCount - 1 'alternativo
'Write #1, Left(Right(WouldBE_DEBUG.File_analizzato_name.List(i), Len(WouldBE_DEBUG.File_analizzato_name.List(i)) - 1), Len(WouldBE_DEBUG.File_analizzato_name.List(i)) - 2)
'Print #1, WouldBE_DEBUG.File_analizzato_name.List(i) ' opzione
Print #1, WouldBe_PDM.Lista_TOP_DOWN.List(i)
Next i
Close #1

'nota devo aggiungere il progetto alla lista dei progetti. occhio ai nomi

End Sub

Attribute VB_Name = "READ_XML_tools"
Sub READ_XML_sub()
If XML_File = "" Then XML_File = "C:\Users\rbartola\Documents\WORK\CAD_001\PRJList.xml"

'XML_File
' remember to activate xml (Tools -> References -> Microsoft XML, V3.0 (C:\windows\System32\msxml3.dll
'GRANDEEEEEEEEEEEEEEEEEEEEEEE
WouldBe_Debug.XML_Family.Clear

    Dim xmldoc As MSXML2.DOMDocument
    Dim xmlNodeList As MSXML2.IXMLDOMNodeList
    Dim myNode As MSXML2.IXMLDOMNode

    Set xmldoc = New MSXML2.DOMDocument
    xmldoc.async = False
   ' MsgBox XML_File
  ' Debug.Print XML_File
    xmldoc.Load XML_File
   ' xmldoc.Load ("C:\Users\rbartola\Documents\WORK\CAD_001\PRJList.xml")
    Set xmlNodeList = xmldoc.selectNodes("//Family_Name")
    If Not (xmlNodeList Is Nothing) Then
        For Each myNode In xmlNodeList
            Debug.Print myNode.Text
       '     If myNode.Text = "8S0.823.509.7777" Then
       '         myNode.Text = "ROBERTO"
       '         xmldoc.Save "C:\Users\rbartola\Documents\WORK\PRJList_OUT.xml"
       '         End If
       WouldBe_Debug.XML_Family.AddItem myNode.Text
             
       
        Next myNode
    End If
    Set xmldoc = Nothing
    
'Dim selectedIndex As Integer
'selectedIndex = WouldBe_Debug.XML_Family.selectedIndex
'Dim selectedItem As Object
'selectedItem = WouldBe_Debug.XML_Family.selectedItem
'    MessageBox.Show ("Selected Item Text: " & selectedItem.ToString() & Microsoft.VisualBasic.Constants.vbCrLf & "Index: " & selectedIndex.ToString())
    
    
    
'Call READ_XML_PRG

End Sub

Sub READ_XML_PRG()
'If XML_File = "" Then XML_File = "C:\Users\rbartola\Documents\WORK\CAD_001\PRJList.xml"

'XML_File
' remember to activate xml (Tools -> References -> Microsoft XML, V3.0 (C:\windows\System32\msxml3.dll
'GRANDEEEEEEEEEEEEEEEEEEEEEEE

'Dim selectedIndex As Integer
'selectedIndex = WouldBe_Debug.XML_Family.selectedIndex
'Dim selectedItem As Object
'selectedItem = WouldBe_Debug.XML_Family.selectedItem
'    MessageBox.Show ("Selected Item Text: " & selectedItem.ToString() & Microsoft.VisualBasic.Constants.vbCrLf & "Index: " & selectedIndex.ToString())
Family_selected = ""
 Family_selected = WouldBe_Debug.XML_Family.Value
 Debug.Print Family_selected


WouldBe_Debug.XML_PRJ.Clear

    Dim xmldoc As MSXML2.DOMDocument
    Dim xmlNodeList As MSXML2.IXMLDOMNodeList
    Dim myNode As MSXML2.IXMLDOMNode


    Set xmldoc = New MSXML2.DOMDocument
    xmldoc.async = False
   ' MsgBox XML_File
 '  Debug.Print XML_File
    xmldoc.Load XML_File
   ' xmldoc.Load ("C:\Users\rbartola\Documents\WORK\CAD_001\PRJList.xml")
'    Set xmlNodeList = xmldoc.selectNodes("//" & Family_selected)
    Set xmlNodeList = xmldoc.selectNodes("//PRJ_Name")
    
    If Not (xmlNodeList Is Nothing) Then
        For Each myNode In xmlNodeList
        
        
 '           Set xmlSUBNodeList = xmlNodeList.selectNodes("//" & Family_selected)
       Set xmlSUBNodeList = xmlNodeList.selectNodes("//Tail gate latches")
    If Not (xmlSUBNodeList Is Nothing) Then
        For Each mySUBNode In xmlSUBNodeList
        
       WouldBe_Debug.XML_PRJ.AddItem mySUBNode.Text
   Debug.Print Family_selected & "->" & mySUBNode.Text
       
        Next mySUBNode
       
    End If
        
        Next myNode
        
       
    End If
    Set xmldoc = Nothing

End Sub

Attribute VB_Name = "TopDownCreate"
'eliminabile?

'Sub Check_TopDown_go()
'' Set the CATIA popup file alerts to False
'CATIA.DisplayFileAlerts = False
'' oppure metto in read invece che open
'
'WouldBE_DEBUG.File_analizzato_name.Clear
'WouldBE_PDM.Lista_Bottom_up.Clear
'WouldBE_DEBUG.Cercato_file_OUT.Caption = ""
'
'If path = "" Then
'path = "C:\Users\rbartola\Documents\WORK\CAD_001"
'End If
'' directory in cui sono i file CAD
'If LocalDir = "" Then
'LocalDir = path
'End If
'If CADDIR = "" Then
'CADDIR = "File_CAD"
'End If
'filadalavorare = EstraiFile(CATIA.ActiveDocument.FullName)
'WouldBE_DEBUG.File_analizzato_name.AddItem filadalavorare
'WouldBE_PDM.Lista_Bottom_up.AddItem filadalavorare
'WouldBE_DEBUG.Cercato_file_OUT.Caption = filadalavorare
'
'FileDaRiaprireAllaFine = CATIA.ActiveDocument.FullName
''commenta per non vedere
''If WouldBE_DEBUG.Visible = False Then WouldBE_DEBUG.Show vbModeless
'Call Dir_current_RB_go_drw ' da creare, copio il...go e attivo solo il drw
''WouldBE_DEBUG.CheckFigli1.Clear
'WouldBE_DEBUG.CheckFigli2.Clear
'WouldBE_DEBUG.CheckFigli3.Clear
'WouldBE_DEBUG.CheckFigli4.Clear
'WouldBE_DEBUG.CheckFigli2.AddItem filadalavorare'
'
''Prova loop - rb001
'Numero_giri = 0
'
'' devo popolare lista2 Call AnalyseLink
'Call AnalyseLink
'For j = 0 To WouldBE_DEBUG.CheckFigli4.ListCount - 1
'WouldBE_DEBUG.CheckFigli2.AddItem WouldBE_DEBUG.CheckFigli4.List(j)
'Next j
'
'For j = 0 To WouldBE_DEBUG.CheckFigli2.ListCount - 1
'Uguale = 0
'For i = 0 To WouldBE_DEBUG.File_analizzato_name.ListCount - 1
'If WouldBE_DEBUG.CheckFigli2.List(j) = WouldBE_DEBUG.File_analizzato_name.List(i) Then Uguale = 1
'Next i
'If Uguale = 0 Then WouldBE_DEBUG.File_analizzato_name.AddItem WouldBE_DEBUG.CheckFigli2.List(j)
'Next j
'
'
'LoopRB:
'Numero_file_aggiunti = 0
'Numero_giri = Numero_giri + 1
''cosa chiamo?
'
'
'
'
'Call Check_topdown_loop
'
'
''ora devo loopare tutto
''--------------------------devi mettere la richiesta nuovo loop
'Dimmi = MsgBox("Vuoi fare un nuovo giro? Numero giri=" & Numero_giri & " file aggiunti questo giro: " & Numero_file_aggiunti & " ?", vbYesNo, "Write confirm")
'If Dimmi = vbYes Then GoTo LoopRB
'
'
'endloop:
'
''tutto finito, riapri il documento iniziale
'CATIA.Documents.Open (FileDaRiaprireAllaFine)
'CATIA.DisplayFileAlerts = True
'
'End Sub

Sub Dir_current_RB_go_drw()
'popola la lista con la dir corrente cad


'provo a ripulire
''directory in cui sono i progetti -----------------------------------Funziona  !!!!!!!!!!!!!!!!
'If path = "" Then
'path = "C:\Users\rbartola\Documents\WORK\CAD_001"
'End If
'' directory in cui sono i file CAD
'If LocalDir = "" Then
'LocalDir = path
'End If
'If CADDIR = "" Then
'CADDIR = "File_CAD"
'End If
'fino qui

LocaldirectoryDaListare = LocalDir & "\" & CADDIR
'MsgBox LocaldirectoryDaListare
WouldBe_Debug.CheckFigli1.Clear
file_name = Dir$(LocaldirectoryDaListare & "\*.*", vbDirectory)
'file_name = Dir$(strDrive & "\*.*", vbDirectory)
'directory in cui sono i progetti -----------------------------------Funziona  !!!!!!!!!!!!!!!!
For i = 1 To 100
 file_name = Dir$()
    If Len(file_name) = 0 Then Exit For
     If Not (Left(file_name, 2) = "..") Then
     'verifica sia catpart o catproduct o catdrawing
'     If Right(file_name, 7) = "CATPart" Then WouldBE_DEBUG.CheckFigli1.AddItem file_name
'     If Right(file_name, 10) = "CATProduct" Then WouldBE_DEBUG.CheckFigli1.AddItem file_name
     If Right(file_name, 10) = "CATDrawing" Then WouldBe_Debug.CheckFigli1.AddItem file_name
     'WouldBE_DEBUG.CheckFigli1.AddItem file_name
'          WouldBE_DEBUG.CheckFigli1.AddItem i & "-" & Len(file_name) & "-" & file_name
     End If
Next i

End Sub

Sub Check_topdown_loop()
LocaldirectoryRB = LocalDir & "\" & CADDIR

  For r = 0 To WouldBe_Debug.CheckFigli1.ListCount - 1
DocFullName_RB = LocaldirectoryRB & "\" & WouldBe_Debug.CheckFigli1.List(r)
'MsgBox DocFullName_RB
'CATIA.Documents.Open DocFullName_RB
CATIA.Documents.Open (DocFullName_RB)
Call AnalyseLink
CATIA.ActiveDocument.Close

For j = 0 To WouldBe_Debug.CheckFigli2.ListCount - 1
For k = 0 To WouldBe_Debug.CheckFigli4.ListCount - 1
If WouldBe_Debug.CheckFigli4.List(k) = WouldBe_Debug.CheckFigli2.List(j) Then
'For l = 0 To WouldBE_DEBUG.CheckFigli3.ListCount - 1
'If WouldBE_DEBUG.CheckFigli2.List(j) <> WouldBE_DEBUG.CheckFigli3.List(l) Then WouldBE_DEBUG.CheckFigli3.AddItem WouldBE_DEBUG.CheckFigli2.List(j)
WouldBe_Debug.CheckFigli3.AddItem WouldBe_Debug.CheckFigli1.List(r)
'Next l
End If

Next k
Next j

'Set oStiDBItem = oStiEngine.GetStiDBItemFromAnyObject(CATIA.ActiveDocument)


'                'Open the drawing and get at the root parameters
'                Set objDwgDoc = CATIA.Documents.Open(objFile.Path)
'                Set objParams = objDwgDoc.Parameters.RootParameterSet.AllParameters
  
  
'poi anra bene
  'Call AnalyseSubProduct(oStiDBItem, CATIA.ActiveDocument.FullName, "")
'Call AnalyseSubProduct(oStiDBItem, CATIA.ActiveDocument.FullName, "")
WouldBe_Debug.CheckFigli4.Clear

Next r

'CATIA.Documents.Open (FileDaRiaprireAllaFine)


End Sub
Sub Check_TopDown_go2()
WouldBe_Debug.File_analizzato_name.Clear
WouldBe_PDM.Lista_TOP_DOWN.Clear
WouldBe_Debug.Cercato_file_OUT.Caption = ""
filadalavorare = EstraiFile(CATIA.ActiveDocument.FullName)
WouldBe_Debug.File_analizzato_name.AddItem filadalavorare
WouldBe_PDM.Lista_TOP_DOWN.AddItem filadalavorare
WouldBe_Debug.Cercato_file_OUT.Caption = filadalavorare

FileDaRiaprireAllaFine = CATIA.ActiveDocument.FullName
'replace Lista_Bottom_up con Lista_TOP_DOWN - fatto
' aggiungi File_analizzato_name ad ogni Lista_TOP_DOWN

CATIA.DisplayFileAlerts = False

'If WouldBE_DEBUG.Visible = False Then WouldBE_DEBUG.Show vbModeless
Call Dir_current_RB_go_drw ' da creare, copio il...go e attivo solo il drw
Call AnalyseLink

For j = 0 To WouldBe_Debug.CheckFigli4.ListCount - 1
Uguale = 0
For i = 0 To WouldBe_Debug.CheckFigli2.ListCount - 1
If WouldBe_Debug.CheckFigli2.List(i) = WouldBe_Debug.CheckFigli4.List(j) Then Uguale = 1
Next i
If Uguale = 0 Then WouldBe_Debug.CheckFigli2.AddItem WouldBe_Debug.CheckFigli4.List(j)
Next j
WouldBe_Debug.CheckFigli4.Clear

Call Check_topdown_loop

For i = 0 To WouldBe_Debug.CheckFigli2.ListCount - 1
Uguale = 0
For j = 0 To WouldBe_PDM.Lista_TOP_DOWN.ListCount - 1
If WouldBe_Debug.CheckFigli2.List(i) = WouldBe_PDM.Lista_TOP_DOWN.List(j) Then Uguale = 1
Next j
If Uguale = 0 Then
WouldBe_PDM.Lista_TOP_DOWN.AddItem WouldBe_Debug.CheckFigli2.List(i)
WouldBe_Debug.File_analizzato_name.AddItem WouldBe_Debug.CheckFigli2.List(i)
End If
Next i

For i = 0 To WouldBe_Debug.CheckFigli3.ListCount - 1
Uguale = 0
For j = 0 To WouldBe_PDM.Lista_TOP_DOWN.ListCount - 1
If WouldBe_Debug.CheckFigli3.List(i) = WouldBe_PDM.Lista_TOP_DOWN.List(j) Then Uguale = 1
Next j
If Uguale = 0 Then
WouldBe_PDM.Lista_TOP_DOWN.AddItem WouldBe_Debug.CheckFigli3.List(i)
WouldBe_Debug.File_analizzato_name.AddItem WouldBe_Debug.CheckFigli3.List(i)
End If

Next i

CATIA.DisplayFileAlerts = True

End Sub

Attribute VB_Name = "Tortoise_roberto"
' Contents class hide Workbook, Documents and Presentations.
''RB Dim mContents As New Contents

' File Open Mode that is set by the user
'Public gCommitFileOpenMode As Integer

' :Function:     Execute TortoiseSVN shell Command
' :Return value: Always return True
Function ExecTsvnCmd_RB(ByVal TsvnCmd As String, ByVal ContFileFullName As String) As Boolean
  ' TortoiseProc.exe path
  Dim TsvnProcPath  As String
  Dim TsvnProc      As String
  ' Tsvn Command Parameter
  Dim TsvnCmdParam  As String
  ' Tsvn Path Parameter
  Dim TsvnPathParam As String
  ' Return value
  Dim Ret           As Integer
  ' WScript.Shell Object
  Dim WsShellObj    As Object
  ' ActiveContent class object
  ''RB Dim ActiveContent As New ActiveContent
  Dim TsvnProgressDlgOption As String
'MsgBox "comando " & TsvnCmd & "opzione " & ContFileFullName
  Set WsShellObj = CreateObject("WScript.Shell")
  If WsShellObj Is Nothing Then
    MsgBox "Failed to CreateObject - WScript.Shell."
    Exit Function
  End If

  'TsvnProcPath = WsShellObj.RegRead("HKEY_LOCAL_MACHINE\SOFTWARE\TortoiseSVN\ProcPath")
  Const HKEY_LOCAL_MACHINE = &H80000002
  TsvnProcPath = ReadRegStr(HKEY_LOCAL_MACHINE, "SOFTWARE\TortoiseSVN", "ProcPath", 64)

  If Len(TsvnProcPath) = 0 Then
    MsgBox "Failed to read TortoiseSVN path from registory."
  End If

  TsvnProc = """" & TsvnProcPath & """"
  TsvnCmdParam = "/command:" & TsvnCmd & " /notempfile "

  If Len(ContFileFullName) = 0 Then
   TsvnPathParam = "/path:" & """" & ActiveContent.GetFullName & """"
 '     TsvnPathParam = "/path:" & """" & PathRB & """"
  Else
    TsvnPathParam = "/path:" & """" & ContFileFullName & """"
  '    TsvnPathParam = "/path:" & """" & Path & """"
  
  End If

'  TsvnProgressDlgOption = "/closeonend:" & GetCiAutoCloseProgressDlg(True)
  TsvnProgressDlgOption = "/closeonend: 0"

  Ret = WsShellObj.Run(TsvnProc & TsvnCmdParam & TsvnPathParam _
                       & TsvnProgressDlgOption, , True)
  Set WsShellObj = Nothing
  ' MsgBox Ret & ", " & Err.Number & ", " & Err.Description
  ' Unfortunately TSVN commands always return 0 even if they fail.
  ' So, this function returns True always.
 ' MsgBox Path
  ExecTsvnCmd_RB = True
End Function
'%TORTOISE% /command:update /path:"%STRINGA%" /logmsg:"test log message" /closeonend:0
' Reads a REG_SZ value from the local computer's registry using WMI.
' Parameters:
' RootKey - The registry hive (see http://msdn.microsoft.com/en-us/library/aa390788(VS.85).aspx for a list of possible values).
' Key - The key that contains the desired value.
' Value - The value that you want to get.
' RegType - The registry bitness: 32 or 64.
'
Function ReadRegStr(RootKey, Key, Value, RegType)
Dim oCtx, oLocator, oReg, oInParams, oOutParams

Set oCtx = CreateObject("WbemScripting.SWbemNamedValueSet")
oCtx.Add "__ProviderArchitecture", RegType

Set oLocator = CreateObject("Wbemscripting.SWbemLocator")
Set oReg = oLocator.ConnectServer("", "root\default", "", "", , , , oCtx).Get("StdRegProv")

Set oInParams = oReg.Methods_("GetStringValue").InParameters
oInParams.hDefKey = RootKey
oInParams.sSubKeyName = Key
oInParams.sValueName = Value

Set oOutParams = oReg.ExecMethod_("GetStringValue", oInParams, , oCtx)

ReadRegStr = oOutParams.sValue
End Function

Attribute VB_Name = "WW_EsportaTutti2DpdfDXF"
Sub CATMain()
'============================================================================================================================================
'********************************************************************************************************************************************
'
' Function: PDF export of current sheet
' Version: 000 del 08/06/2015
' Author: Roberto Bartola robertobartola@gmail.com
'
'********************************************************************************************************************************************
'============================================================================================================================================
Dim oFSO
Set oFSO = CreateObject("Scripting.FileSystemObject")
'This code assumes a drawing is already open!
Dim objDwgDoc As DrawingDocument
Dim objSheet As DrawingSheet
Dim objView As DrawingView
Dim objText As DrawingText
Dim intCount As Integer
Dim intIndex As Integer
'Get at the active drawing
Set objDwgDoc = CATIA.ActiveDocument
Set sheetcorr = objDwgDoc.Sheets.ActiveSheet
'Documento corrente
directorycorrente = EstraiDirectory(objDwgDoc.Sheets.Name)
'MsgBox objDwgDoc.Sheets.Name & " " & directorycorrente

TmpDirectoryExport = directorycorrente & "\tmpexportpdf"
'crea directory se non esiste
If Not oFSO.FolderExists(TmpDirectoryExport) Then
   Presente = 0
oFSO.CreateFolder (TmpDirectoryExport)
'MsgBox "La dir non esisteva, creata"
Else
Presente = 1
'MsgBox "La dir esiste"
End If

'Esporta tutti i pdf
Set DrawingDocument = CATIA.ActiveDocument
'DrawingDocument.ExportData NuovoFilename, "pdf"
DrawingDocument.ExportData TmpDirectoryExport & "\" & Left(EstraiFile(objDwgDoc.Sheets.Name), Len(EstraiFile(objDwgDoc.Sheets.Name)) - 11) & ".pdf", "pdf"
'If Presente = 1 Then MsgBox "La dir esiste"
NomeSheetCorrente = objDwgDoc.Sheets.ActiveSheet.Views.Name
'MsgBox "Current sheet name = " & NomeSheetCorrente
NomeSheetCorrenteReplaced = Replace(NomeSheetCorrente, ".", "_")

PdfOKName = Left(EstraiFile(objDwgDoc.Sheets.Name), Len(EstraiFile(objDwgDoc.Sheets.Name)) - 11) & "_" & NomeSheetCorrenteReplaced & ".pdf"
PdfExportName = Left(EstraiFile(objDwgDoc.Sheets.Name), Len(EstraiFile(objDwgDoc.Sheets.Name)) - 11) & ".pdf"
'MsgBox "File giusto = " & PdfOKName
If Not oFSO.FileExists(directorycorrente & "\" & PdfExportName) Then
  FileCopy TmpDirectoryExport & "\" & PdfOKName, directorycorrente & "\" & PdfExportName
Else
  Dimmi = MsgBox("Attenzione il file esiste già. Rimpiazzarlo?", vbYesNo, "Write confirm")
  If Dimmi = vbYes Then
     Kill directorycorrente & "\" & PdfExportName
     FileCopy TmpDirectoryExport & "\" & PdfOKName, directorycorrente & "\" & PdfExportName
  End If
End If
'rimuovi tutto quanto creato
'MsgBox TmpDirectoryExport & "\" & Left(EstraiFile(objDwgDoc.Sheets.Name), Len(EstraiFile(objDwgDoc.Sheets.Name)) - 11) & "*.pdf"
    If Presente = 0 Then
    On Error Resume Next
   Kill TmpDirectoryExport & "\" & Left(EstraiFile(objDwgDoc.Sheets.Name), Len(EstraiFile(objDwgDoc.Sheets.Name)) - 11) & "*.pdf"
'    Kill "TmpDirectoryExport\*.*"    ' delete all files in the folder
    RmDir TmpDirectoryExport & "\" ' delete folder
   'On Error GoTo 0
    Else
    Kill TmpDirectoryExport & "\" & Left(EstraiFile(objDwgDoc.Sheets.Name), Len(EstraiFile(objDwgDoc.Sheets.Name)) - 11) & "*.pdf"
   End If
    
'rimuovi tutto quanto creato
'If Presente = 0 Then
'On Error Resume Next
'Kill "TmpDirectoryExport\*.*"    ' delete all files in the folder
'RmDir "TmpDirectoryExport\" ' delete folder
'On Error GoTo 0
'End If


End Sub


Sub CheckTextValue_esportaecontafogli()
'============================================================================================================================================
'********************************************************************************************************************************************
'
' Function: Current sheet export
' Version: 000 del 08/06/2015
' Author: Roberto Bartola robertobartola@gmail.com
'
'********************************************************************************************************************************************
'============================================================================================================================================
Dim oFSO
Set oFSO = CreateObject("Scripting.FileSystemObject")


 
'This code assumes a drawing is already open!
 
Dim objDwgDoc As DrawingDocument
Dim objSheet As DrawingSheet
Dim objView As DrawingView
Dim objText As DrawingText
Dim intCount As Integer
Dim intIndex As Integer
 
'Get at the active drawing
Set objDwgDoc = CATIA.ActiveDocument
Set sheetcorr = objDwgDoc.Sheets.ActiveSheet
'Documento corrente
directorycorrente = EstraiDirectory(objDwgDoc.Sheets.Name)
MsgBox objDwgDoc.Sheets.Name & " " & directorycorrente
'Dir$(Mydir & "\*.*")
TmpDirectoryExport = directorycorrente & "\tmpexportpdf"

'If Len(Dir(TmpDirectoryExport, vbDirectory)) = 0 Then
'   MkDir TmpDirectoryExport
'   Presente = 0
'MsgBox "La dir non esisteva, creata"
'Else
'Presente = 1
'MsgBox "La dir esiste"
'End If

'più elegante crea directory
If Not oFSO.FolderExists(TmpDirectoryExport) Then
   Presente = 0
oFSO.CreateFolder (TmpDirectoryExport)
MsgBox "La dir non esisteva, creata"
Else
Presente = 1
MsgBox "La dir esiste"
End If

'NomeDelFileConEstenzione = EstraiFile(objDwgDoc.Sheets.Name)
'NomeDelFileConEstenzione = objDwgDoc.Sheets.Name
'NomeDelFileNuovaEstenzione = Left(NomeDelFileConEstenzione, Len(NomeDelFileConEstenzione) - 11) & ".pdf"
'MsgBox NomeDelFileNoEstenzione & " " & NomeDelFileConEstenzione
'NuovoFilename = TmpDirectoryExport & "\" & NomeDelFileNuovaEstenzione
'MsgBox """" & NuovoFilename & """"

'Esporta tutti i pdf
Set DrawingDocument = CATIA.ActiveDocument
'DrawingDocument.ExportData NuovoFilename, "pdf"
DrawingDocument.ExportData TmpDirectoryExport & "\" & Left(EstraiFile(objDwgDoc.Sheets.Name), Len(EstraiFile(objDwgDoc.Sheets.Name)) - 11) & ".pdf", "pdf"
'If Presente = 1 Then MsgBox "La dir esiste"

'Get at the first sheet or notify user if none are found
'intCount = objDwgDoc.Sheets.Count
intCount = objDwgDoc.Sheets.Count
'MsgBox intCount

If intCount = 0 Then
   Set objSheet = objDwgDoc.Sheets.Item(1)
  MsgBox "This drawing has no sheets!", 16, "Error"
Else
'   MsgBox "This drawing has no sheets!", 16, "Error"
    MsgBox "This drawing has " & intCount & " sheets " & "Current sheet name = " & objDwgDoc.Sheets.ActiveSheet.Views.Name
  ' Exit Sub
End If
 
MsgBox "Foglio attuale tot view: " & sheetcorr.Views.Count - 2
 
'For j = 0 To intCount
'objDwgDoc.Activate
'Next j
 k = 0
'objDwgDoc.Sheets.ActiveSheet.Application.Documents.Open
'objDwgDoc.ExportData   .Sheets .Application.ExportData
 For Each View In objDwgDoc.Sheets.ActiveSheet.Views
 k = k + 1
If k > 2 Then MsgBox "Sheet " & objDwgDoc.Sheets.ActiveSheet.Views.Name & " View numero " & k - 2 & " " & View.Name
'MsgBox "numero " & k & objDwgDoc.Sheets.ActiveSheet.Views.Name
' MsgBox View
 Next
 
 
 l = 0
For Each sheet In objDwgDoc.Sheets
l = l + 1
MsgBox l & " " & objDwgDoc.Sheets.ActiveSheet.Name & " " & objDwgDoc.Sheets.Name
'MsgBox objDwgDoc.Sheets.Name & " " & l
Next
 
 
 
'Get at the first view or notify user if none are found
'intIndex = objSheet.Views.Count
'intIndex = objSheet.Views.Count
'intIndex = 0
'
' deleta da qui in giu
End Sub


'intIndex = sheetcorr.Views.Count
'
'If intIndex = 0 Then
'   Set objView = objSheet.Views.Item(1)
'MsgBox "The first sheet has no views!", 16, "Error"
'Else
'MsgBox "This Sheets has " & intIndex & " views"
'   'MsgBox "The first sheet has no views!", 16, "Error"
''MsgBox "Numero Views" & objView
'  ' Exit Sub
'End If
'VistaSelezionata = objDwgDoc.Sheets.ActiveSheet.Views.ActiveView.Name
'MsgBox VistaSelezionata'
''
'
'For i = 1 To sheetcorr.Views.Count
''objDwgDoc.Sheets.ActiveSheet.Views.ActiveView.Activate
'MsgBox objDwgDoc.Sheets.ActiveSheet.Views.ActiveView.Name
'A = objDwgDoc.Sheets.ActiveSheet.Views.ActiveView.Name
'MsgBox "Vista numero " & i & " si chiama " & A
'Next i
''objDwgDoc.Sheets.ActiveSheet.Views.ActiveView (VistaSelezionata)
'
''...We need to add some code here to see if there
''...is a drawing text with a value of "Front View"
'
'End Sub


    Sub CATMainSmaino()
    Dim oFSO
    Set oFSO = CreateObject("Scripting.FileSystemObject")

    PathToCATFiles = InputBox("Enter path there CATDrawings-files exist" & vbCrLf, "File", "")

    strComputer = "."
    Set objWMIService = GetObject("winmgmts:" & "{impersonationLevel=impersonate}!\\" & strComputer & "\root\cimv2")
    If Not oFSO.FolderExists(PathToCATFiles & "\PDF") Then
    oFSO.CreateFolder (PathToCATFiles & "\PDF")
    End If
 '   If Not oFSO.FolderExists(PathToCATFiles & "\DWG") Then
 '   oFSO.CreateFolder (PathToCATFiles & "\DWG")
 '   End If

    Set FileList = objWMIService.ExecQuery("Associators of {Win32_Directory.Name='" & PathToCATFiles & "'} Where " & "ResultClass = CIM_DataFile")

    For Each objFile In FileList

    If objFile.Extension = "CATDrawing" Then

    On Error Resume Next
    Set Documents = CATIA.Documents
    Set DrawingDocument = Documents.Open(PathToCATFiles & "\" & objFile.FileName & "." & objFile.Extension)
    'Set DrawingDocument = CATIA.ActiveDocument
    Set DrawingDocument = CATIA.ActiveDocument
    
    
    
    DrawingDocument.ExportData PathToCATFiles & "\PDF\" & objFile.FileName & ".pdf", "pdf"
    
'    DrawingDocument.ExportData PathToCATFiles & "\DWG\" & objFile.FileName & ".dwg", "dwg"
    Set SpecsAndGeomWindow = CATIA.ActiveWindow
    SpecsAndGeomWindow.Close
    Set DrawingDocument = CATIA.ActiveDocument
    DrawingDocument.Close
    End If
    Next

    Wscript.Echo "DWG and PDF files created in subfolders to " & PathToCATFiles
    End Sub

Attribute VB_Name = "WW_ProvaEsportaImmagini"
Sub CATMain()

Dim ObjViewer3D As Viewer3D
Set ObjViewer3D = CATIA.ActiveWindow.ActiveViewer

Dim objCamera3D As Camera3D
Set objCamera3D = CATIA.ActiveDocument.Cameras.Item(1)

ObjViewer3D.Viewpoint3D = objCamera3D.Viewpoint3D

'Input box to name the screen capture image file
Dim partname As String
partname = InputBox("Please name the image.")

'reframe
'objViewer3D.Reframe()


'zoom in
'objViewer3D.ZoomIn()
'objViewer3D.ZoomIn()

'turn off the spec tree
Dim objSpecWindow As SpecsAndGeomWindow
Set objSpecWindow = CATIA.ActiveWindow
objSpecWindow.Layout = catWindowGeomOnly

'Toggle Compass
CATIA.StartCommand ("Compass")

'change background color to white
Dim DBLBackArray(2)
'ObjViewer3D.GetBackgroundColor (DBLBackArray)
Dim dblWhiteArray(2)
dblWhiteArray(0) = 1
dblWhiteArray(1) = 1
dblWhiteArray(2) = 1
'ObjViewer3D.PutBackgroundColor (dblWhiteArray)

'clear selection for picture
'CATIA.ActiveDocument.Selection.Clear()

'increase to fullscreen to obtain maximum resolution
ObjViewer3D.FullScreen = True

'file location to save image
Dim fileloc As String
fileloc = "C:\"

Dim exten As String
exten = ".bmp"

Dim strName As String
strName = fileloc & partname & exten

'MsgBox strname

'take picture
ObjViewer3D.CaptureToFile 4, strName

ObjViewer3D.FullScreen = False

'change background color back
'ObjViewer3D.PutBackgroundColor (DBLBackArray)

'turn the spec tree back on
objSpecWindow.Layout = catWindowSpecsAndGeom

'toggle compass
CATIA.StartCommand ("Compass")

End Sub

Attribute VB_Name = "WW_Zumma_per_exportimage"
'Language = "VBSCRIPT"
Sub CATMain()

Dim specsAndGeomWindow1 As Window
Set specsAndGeomWindow1 = CATIA.ActiveWindow

Dim viewer3D1 As Viewer
Set viewer3D1 = specsAndGeomWindow1.ActiveViewer

viewer3D1.Reframe

Dim viewpoint3D1 As Viewpoint3D
Set viewpoint3D1 = viewer3D1.Viewpoint3D

End Sub

Attribute VB_Name = "WouldBe_Debug"
Attribute VB_Base = "0{DE39FFE7-F8BB-447F-A118-DFC2DA7492E7}{F61AED57-CD32-496C-90E2-0AE3365704B8}"
Attribute VB_GlobalNameSpace = False
Attribute VB_Creatable = False
Attribute VB_PredeclaredId = True
Attribute VB_Exposed = False
Attribute VB_TemplateDerived = False
Attribute VB_Customizable = False
Private Sub Dir_button_Click()
Call Dir_current_RB_go
End Sub

Private Sub Erase_debug_Click()
Call MostraNascondiDebug
End Sub

Private Sub Esporta_su_File_Click()
Call GO_Esporta_su_File
End Sub

Private Sub Go_PRJ_Click()
Call READ_XML_PRG

End Sub

Private Sub Label14_Click()

End Sub

Private Sub READ_XML_Click()
Call READ_XML_sub
End Sub

Attribute VB_Name = "WouldBe_PDM"
Attribute VB_Base = "0{788E0364-A250-4889-A96E-A3C29A7BA8D4}{3C5AD940-2424-4CEA-9914-AE1D4018CC19}"
Attribute VB_GlobalNameSpace = False
Attribute VB_Creatable = False
Attribute VB_PredeclaredId = True
Attribute VB_Exposed = False
Attribute VB_TemplateDerived = False
Attribute VB_Customizable = False

'Private Sub AnalyseLink_go_Click()
'Call AnalyseLink
'End Sub

Private Sub ApriFile_alltypes_Click()
'UserForm2.Show vbModal
Call LeggiFileTxt
End Sub

Private Sub Button_ApriCartella_Click()
Call ApriDir2
End Sub

Private Sub Button_ApriCartellaCAD_Click()
Call ApriDir
End Sub

Private Sub ButtonShowLog_Click()
Call DoShowLog
End Sub

Private Sub ButtonUpdata_Click()
Call Do_CheckOut
End Sub

Private Sub Check_bottomUp_button_Click()
Call Check_bottomUp_go
End Sub

Private Sub Check_Debug_Click()
Call MostraNascondiDebug

End Sub

Private Sub Check_topdown_button_Click()
Call Check_TopDown_go2
End Sub

Private Sub CommandButton1_Click()
Call CambiaDirectory
End Sub

Private Sub CommandButton10_Click()
Call GO_Esporta_su_File_PRJ
End Sub

Private Sub CommandButton12_Click()
'visualizza tutto il SUB_form nascosto
'label totale
If WouldBe_PDM.ModificaListeProgetto_Label.Visible = False Then WouldBe_PDM.ModificaListeProgetto_Label.Visible = True Else WouldBe_PDM.ModificaListeProgetto_Label.Visible = False

'Bottom up
If WouldBe_PDM.Label_bottomUp.Visible = False Then WouldBe_PDM.Label_bottomUp.Visible = True Else WouldBe_PDM.Label_bottomUp.Visible = False ' label
If WouldBe_PDM.CommandButton8.Visible = False Then WouldBe_PDM.CommandButton8.Visible = True Else WouldBe_PDM.CommandButton8.Visible = False 'comando esporta lista
If WouldBe_PDM.Check_bottomUp_button.Visible = False Then WouldBe_PDM.Check_bottomUp_button.Visible = True Else WouldBe_PDM.Check_bottomUp_button.Visible = False ' bottone check
If WouldBe_PDM.Lista_Bottom_up.Visible = False Then WouldBe_PDM.Lista_Bottom_up.Visible = True Else WouldBe_PDM.Lista_Bottom_up.Visible = False ' listbox

'Top Down
If WouldBe_PDM.Label_TopDown.Visible = False Then WouldBe_PDM.Label_TopDown.Visible = True Else WouldBe_PDM.Label_TopDown.Visible = False
If WouldBe_PDM.CommandButton10.Visible = False Then WouldBe_PDM.CommandButton10.Visible = True Else WouldBe_PDM.CommandButton10.Visible = False 'comando esporta lista
If WouldBe_PDM.Check_topdown_button.Visible = False Then WouldBe_PDM.Check_topdown_button.Visible = True Else WouldBe_PDM.Check_topdown_button.Visible = False 'bottone check
If WouldBe_PDM.Lista_TOP_DOWN.Visible = False Then WouldBe_PDM.Lista_TOP_DOWN.Visible = True Else WouldBe_PDM.Lista_TOP_DOWN.Visible = False ' listbox

End Sub

Private Sub CommandButton2_Click()
Call AggiungiFileCADalPRJ
End Sub

'Private Sub CommandButton3_Click()
'Call listafiledirectory
'End Sub

'Private Sub CommandButton4_Click()
'Call Ciriprovo
'End Sub

Private Sub CommandButton5_Click()
Call AnalyseLink
End Sub

'Private Sub CommandButton6_Click()
'Call Elenca_linked_parts_ORI_funzionava
'End Sub


Private Sub CommandButton8_Click()
Call GO_Esporta_su_File
End Sub

Private Sub CommandButtonCheck_prj_Click()
Call ControllaFileCadQualePRJ
End Sub

'Private Sub GetDrawingPointedPart_Click()
'Call GetDrawingPointedPartSub
'End Sub

'Private Sub GetProductPointedPart_Click()
'Call Elenca_linked_parts
'
'End Sub

Private Sub ListBox1_Click()
'SelectedPrj_Numeroselezionato = 1
SelectedPrj_Numeroselezionato = 0

  For r = 0 To WouldBe_PDM.ListBox1.ListCount - 1
             If WouldBe_PDM.ListBox1.Selected(r) Then
              SelectedPrj_Numeroselezionato = r
          End If
        
    Next r

End Sub

Attribute VB_Name = "funziona_checkDOWN"
 
 Sub bho()
  Dim oStiEngine As StiEngine
 Set oStiEngine = CATIA.GetItem("CAIEngine")
 Dim oFatherStiDBItem As StiDBItem
 Set oFatherStiDBItem = oStiEngine.GetStiDBItemFromCATBSTR("C:\Users\rbartola\Documents\WORK\CAD_001\File_CAD\Part6.CATPart")
 Dim oStiDBChildren As StiDBChildren
 Set oStiDBChildren = oFatherStiDBItem.GetChildren()
MsgBox oStiDBChildren
'Dim oLinkType As CATBSTR
' MsgBox oStiDBChildren.LinkType(3)
 'MsgBox oLinkType
 End Sub


Sub AnalyseLink()
'''OOOK-----------------------------------------------------------------FUNZIONA !!!!!!! Grande !!!!!!!!!!!!!!!!!!!!!
'WouldBE_DEBUG.CheckFigli4.Clear
'If WouldBE_DEBUG.Visible = False Then WouldBE_DEBUG.Show vbModeless
'    Set CATIA = GetObject("CATIA.Application")
    Dim oStiEngine ' As StiEngine
    Set oStiEngine = CATIA.GetItem("CAIEngine")
    Dim oStiDBItem ' As StiDBItem
    Set oStiDBItem = oStiEngine.GetStiDBItemFromAnyObject(CATIA.ActiveDocument)
    Debug.Print CATIA.ActiveDocument.FullName
    Call AnalyseSubProduct(oStiDBItem, CATIA.ActiveDocument.FullName, "")
'MsgBox CATIA.ActiveDocument.FullName
End Sub

Sub AnalyseSubProduct(oStiDBItem, FatherName As String, TabStrFather As String)

'''OOOK-----------------------------------------------------------------FUNZIONA !!!!!!! Grande !!!!!!!!!!!!!!!!!!!!!
'''OOOK-----------------------------------------------------------------FUNZIONA !!!!!!! Grande !!!!!!!!!!!!!!!!!!!!!
    Dim i As Integer
    Dim oStiDBChildren
    Dim oStiDBItem2 ' As StiDBItem  -- Smarteam is not SetUp , API recognize , so use AnyObject Type
    Dim SonName As String
    Dim TabStrChildren As String
   
    Set oStiDBChildren = oStiDBItem.GetChildren
    For i = 1 To oStiDBChildren.Count
        Set oStiDBItem2 = oStiDBChildren.Item(i)
        SonName = oStiDBItem2.GetDocumentFullPath
        SonNameSolo = EstraiFile(SonName) ' oStiDBItem2.Name ' come si da il nome da solo? 'DocumentoAttuale = CATIA.ActiveDocument.Name
        TabStrChildren = TabStrFather & "-"
        LinkType = CStr(oStiDBChildren.LinkType(i))
        ' se non è presente nella listbox lo aggiungo
Uguale = 0
For j = 0 To WouldBe_Debug.CheckFigli4.ListCount - 1
If WouldBe_Debug.CheckFigli4.List(j) = SonNameSolo Then Uguale = 1
Next j

If Uguale = 0 Then WouldBe_Debug.CheckFigli4.AddItem SonNameSolo
            ' in Case of Product with Subcompoent   Or Product with CATIA V4 model
            ' recursive Analyse to SubProduct
  'tolgo la recursione ?
        FatherName = SonName
           Call AnalyseSubProduct(oStiDBItem2, FatherName, TabStrChildren)
    Next i

End Sub
