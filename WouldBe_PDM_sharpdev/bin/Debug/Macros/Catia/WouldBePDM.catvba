Attribute VB_Name = "Class1"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False

Public Property Get ss() As Variant
Import win32com.client
catapp = win32com.client.Dispatch("CATIA.Application")
Doc = catapp.ActiveDocument.Product
 
product_count = Doc.Products.Count
Print "This example lists all Parts and Subproducts of the first level from a CATProduct."
for products in range(product_count):
Products = Products + 1
Print Doc.Products.Item(Products).Name, ":"
part_count = Doc.Products.Item(Products).Products.Count
for parts in range(part_count):
parts = parts + 1
Print " ", Doc.Products.Item(Products).Products.Item(parts).Name
End Property

Public Property Let ss(ByVal vNewValue As Variant)

End Property

Attribute VB_Name = "EsportaTuttiSTP"
Public TMPfile As String
Public RowIndex
Public DirectoryExportSTP As String
Public NameOfThePart As String


Sub CatMain()

Dim oFSO
Set oFSO = CreateObject("Scripting.FileSystemObject")

Dim strEnviron As String
Dim Indx As Integer
Dim pos As Integer

RowIndex = 1
Indx = 1
Counter = 0

Set Document = CATIA.ActiveDocument
DocFullName = Document.FullName


If Right(DocFullName, 10) = "CATDrawing" Then
MsgBox "I need a 3D to generate Image"
Exit Sub
Else

'Documento corrente
directorycorrente = EstraiDirectory(DocFullName)
'MsgBox objDwgDoc.Sheets.Name & " " & directorycorrente
DirectoryExportSTP = directorycorrente & "\STEPExport"
If Not oFSO.FolderExists(DirectoryExportSTP) Then
   Presente = 0
oFSO.CreateFolder (DirectoryExportSTP)
End If

'kore
NameOfThePart = EstraiFile(CATIA.ActiveDocument.FullName)
CATIA.DisplayFileAlerts = False

   Call SteppaFile
   
CATIA.DisplayFileAlerts = True
End If

End Sub
Sub SteppaFile()
'MsgBox (Right(NameOfThePart, 10))

If Right(NameOfThePart, 7) = "CATPart" Then NameOfThePartOK = Left(NameOfThePart, Len(NameOfThePart) - 8)
If Right(NameOfThePart, 10) = "CATProduct" Then NameOfThePartOK = Left(NameOfThePart, Len(NameOfThePart) - 11)
'MsgBox (NameOfThePartOK)

TMPfile = DirectoryExportSTP & "\" & NameOfThePartOK & ".stp"


Set CurrentDocument = CATIA.ActiveDocument

CurrentDocument.ExportData TMPfile, "stp"
End Sub

Attribute VB_Name = "ExportImage"
Public TMPfile As String
Public RowIndex
Public DirectoryExportJPG As String
Public NameOfThePart As String


Sub CatMain()

Dim oFSO
Set oFSO = CreateObject("Scripting.FileSystemObject")

Dim strEnviron As String
Dim Indx As Integer
Dim pos As Integer

RowIndex = 1
Indx = 1
Counter = 0

Set Document = CATIA.ActiveDocument
DocFullName = Document.FullName


If Right(DocFullName, 10) = "CATDrawing" Then
MsgBox "I need a 3D to generate Image"
Exit Sub
Else

'Documento corrente
directorycorrente = EstraiDirectory(DocFullName)
'MsgBox objDwgDoc.Sheets.Name & " " & directorycorrente
DirectoryExportJPG = directorycorrente & "\JPGExport"
If Not oFSO.FolderExists(DirectoryExportJPG) Then
   Presente = 0
oFSO.CreateFolder (DirectoryExportJPG)
End If

'kore
NameOfThePart = EstraiFile(CATIA.ActiveDocument.FullName)
CATIA.DisplayFileAlerts = False

   Call ReadImage
   
CATIA.DisplayFileAlerts = True
End If

End Sub


Sub ReadImage()

If Right(NameOfThePart, 7) = "CATPart" Then NameOfThePartOK = Left(NameOfThePart, Len(NameOfThePart) - 8)
If Right(NameOfThePart, 10) = "CATProduct" Then NameOfThePartOK = Left(NameOfThePart, Len(NameOfThePart) - 11)
'MsgBox (NameOfThePartOK)

'TMPfile = DirectoryExportJPG & "\" & NameOfThePartOK & ".stp"

TMPfile = DirectoryExportJPG & "\" & NameOfThePartOK & ".jpg"
Dim specsAndGeomWindow1 As Window
Set specsAndGeomWindow1 = CATIA.ActiveWindow

Dim viewer3D1 As Viewer
Set viewer3D1 = specsAndGeomWindow1.ActiveViewer

viewer3D1.Reframe
CATIA.StartCommand "Specifications"
CATIA.StartCommand "Compass"

Dim viewpoint3D1 As Viewpoint3D
Set viewpoint3D1 = viewer3D1.Viewpoint3D

viewer3D1.CaptureToFile catCaptureFormatJPEG, TMPfile

CATIA.StartCommand "Specifications"
CATIA.StartCommand "Compass"

End Sub

Attribute VB_Name = "WW_EsportaTutti2DpdfDXF"
Sub CatMain()
'============================================================================================================================================
'********************************************************************************************************************************************
'
' Function: PDF export of current sheet
' Version: 000 del 08/06/2015
' Author: Roberto Bartola robertobartola@gmail.com
'
'********************************************************************************************************************************************
'============================================================================================================================================
Dim oFSO
Set oFSO = CreateObject("Scripting.FileSystemObject")
'This code assumes a drawing is already open!
Dim objDwgDoc As DrawingDocument
Dim objSheet As DrawingSheet
Dim objView As DrawingView
Dim objText As DrawingText
Dim intCount As Integer
Dim intIndex As Integer
'Get at the active drawing

Set Document = CATIA.ActiveDocument
DocFullName = Document.FullName
If Right(DocFullName, 10) <> "CATDrawing" Then
MsgBox "I need a Drawing to generate PDF"
Exit Sub
Else

Set objDwgDoc = CATIA.ActiveDocument
Set sheetcorr = objDwgDoc.Sheets.ActiveSheet

Set drawingSheets1 = objDwgDoc.Sheets

'MsgBox drawingSheets1.Count



'Documento corrente
directorycorrente = EstraiDirectory(objDwgDoc.Sheets.Name)
'MsgBox objDwgDoc.Sheets.Name & " " & directorycorrente
DirectoryExportPDF = directorycorrente & "\PdfExport"
TmpDirectoryExport = directorycorrente & "\tmpexportpdf"
'crea directory se non esiste
If Not oFSO.FolderExists(TmpDirectoryExport) Then
   Presente = 0
oFSO.CreateFolder (TmpDirectoryExport)
'MsgBox "La dir non esisteva, creata"
Else
Presente = 1
'MsgBox "La dir esiste"
End If

If Not oFSO.FolderExists(DirectoryExportPDF) Then
   Presente = 0
oFSO.CreateFolder (DirectoryExportPDF)
'MsgBox "La dir non esisteva, creata"
End If



'Esporta tutti i pdf
Set DrawingDocument = CATIA.ActiveDocument
'DrawingDocument.ExportData NuovoFilename, "pdf"
DrawingDocument.ExportData TmpDirectoryExport & "\" & Left(EstraiFile(objDwgDoc.Sheets.Name), Len(EstraiFile(objDwgDoc.Sheets.Name)) - 11) & ".pdf", "pdf"
'If Presente = 1 Then MsgBox "La dir esiste"
'NomeSheetCorrente = objDwgDoc.Sheets.ActiveSheet.Views.Name
NomeSheetCorrente = objDwgDoc.Sheets.ActiveSheet.Name

NomeSheetCorrenteReplaced = NomeSheetCorrente
If NomeSheetCorrente Like "*.*" Then NomeSheetCorrenteReplaced = Replace(NomeSheetCorrente, ".", "_")
If drawingSheets1.Count > 1 Then
PdfOKName = Left(EstraiFile(objDwgDoc.Sheets.Name), Len(EstraiFile(objDwgDoc.Sheets.Name)) - 11) & "_" & NomeSheetCorrenteReplaced & ".pdf"
PdfExportName = Left(EstraiFile(objDwgDoc.Sheets.Name), Len(EstraiFile(objDwgDoc.Sheets.Name)) - 11) & ".pdf"

Else
PdfOKName = Left(EstraiFile(objDwgDoc.Sheets.Name), Len(EstraiFile(objDwgDoc.Sheets.Name)) - 11) & ".pdf"
PdfExportName = Left(EstraiFile(objDwgDoc.Sheets.Name), Len(EstraiFile(objDwgDoc.Sheets.Name)) - 11) & ".pdf"
End If



If Not oFSO.FileExists(DirectoryExportPDF & "\" & PdfExportName) Then
  FileCopy TmpDirectoryExport & "\" & PdfOKName, DirectoryExportPDF & "\" & PdfExportName
Else
  Dimmi = MsgBox("Attenzione il file esiste già. Rimpiazzarlo?", vbYesNo, "Write confirm")
  If Dimmi = vbYes Then
     Kill DirectoryExportPDF & "\" & PdfExportName
     FileCopy TmpDirectoryExport & "\" & PdfOKName, DirectoryExportPDF & "\" & PdfExportName
  End If
End If



'rimuovi tutto quanto creato
'MsgBox TmpDirectoryExport & "\" & Left(EstraiFile(objDwgDoc.Sheets.Name), Len(EstraiFile(objDwgDoc.Sheets.Name)) - 11) & "*.pdf"
    If Presente = 0 Then
    On Error Resume Next
   Kill TmpDirectoryExport & "\" & Left(EstraiFile(objDwgDoc.Sheets.Name), Len(EstraiFile(objDwgDoc.Sheets.Name)) - 11) & "*.pdf"
'    Kill "TmpDirectoryExport\*.*"    ' delete all files in the folder
    RmDir TmpDirectoryExport & "\" ' delete folder
   'On Error GoTo 0
    Else
    Kill TmpDirectoryExport & "\" & Left(EstraiFile(objDwgDoc.Sheets.Name), Len(EstraiFile(objDwgDoc.Sheets.Name)) - 11) & "*.pdf"
   End If
    

End If


End Sub





Function EstraiDirectory(Percorso)
'============================================================================================================================================
'********************************************************************************************************************************************
'
' Function: Extracts dir name from fullname
' Version: 000 del 08/06/2015
' Author: Roberto Bartola robertobartola@gmail.com
'
'********************************************************************************************************************************************
'============================================================================================================================================
EstraiDirectory = Left(Percorso, Len(Percorso) - Len(Right(Percorso, Len(Percorso) - InStrRev(Percorso, "\"))) - 1)
End Function

Function EstraiFile(Percorso)
'============================================================================================================================================
'********************************************************************************************************************************************
'
' Function: Extracts the filename from fullname
' Version: 000 del 08/06/2015
' Author: Roberto Bartola robertobartola@gmail.com
'
'********************************************************************************************************************************************
'============================================================================================================================================
EstraiFile = Right(Percorso, Len(Percorso) - InStrRev(Percorso, "\"))
End Function

Function ApriFile_RB(Nome)
'============================================================================================================================================
'********************************************************************************************************************************************
'
' Function: Open the file
' Version: 000 del 08/06/2015
' Author: Roberto Bartola robertobartola@gmail.com
'
'********************************************************************************************************************************************
'============================================================================================================================================

Dim FileName As String
Dim documents1 As Documents
Dim Document1 As Document
FileName = Nome
' open the drawing that contains the titleblock that we want
'MsgBox "Nome del file " & FileName
Set documents1 = CATIA.Documents
Set Document1 = documents1.Open(FileName)

'CATIA.Documents.Open(FileName)
'CATIA.Documents.Read()
'CATIA.Documents.Read
End Function
