Attribute VB_Name = "Capturami"
Sub ReadImage()
'Dim TMPfile As String
'TMPfile = VariablesEnvironnementFindTMP2()
'If TMPfile = "" Then TMPfile = "C:\Users\rbartola\AppData\Local\Temp\Currentfile.jpg" 'tmp to remove
TMPfile = Half_Path & "\Temp\Currentfile" & Counter & ".jpg"

Dim specsAndGeomWindow1 As Window
Set specsAndGeomWindow1 = CATIA.ActiveWindow

Dim viewer3D1 As Viewer
Set viewer3D1 = specsAndGeomWindow1.ActiveViewer

viewer3D1.Reframe
'viewer3D1.ZoomIn
'viewer3D1.ZoomIn
'CATIA.StartCommand (Capture)
'Toggle Compass
'CATIA.StartCommand ("Capture...")
'CATIA.StartCommand ("Capture")
CATIA.StartCommand "Specifications"
CATIA.StartCommand "Compass"

Dim viewpoint3D1 As Viewpoint3D
Set viewpoint3D1 = viewer3D1.Viewpoint3D

viewer3D1.CaptureToFile catCaptureFormatJPEG, TMPfile

'Toggle Compass
CATIA.StartCommand "Specifications"
CATIA.StartCommand "Compass"

End Sub

Function VariablesEnvironnementFindTMP2()

Dim strEnviron As String
Dim Indx As Integer
Dim pos As Integer

Indx = 1
strEnviron = Environ(Indx)
Do While strEnviron <> ""
pos = InStr(1, strEnviron, "=")
Find_Variable = Left(strEnviron, pos - 1)
Find_Value = Right(strEnviron, Len(strEnviron) - pos)

'search all the variables

If Find_Variable = "LOCALAPPDATA" Then Half_Path = Find_Value

Indx = Indx + 1
strEnviron = Environ(Indx)
Loop

'If Path = "" Then Path = Half_Path & "\WORK\CAD_001"
' directory in cui sono i file CAD
'If LocalDir = "" Then LocalDir = Path
'If LISTAPRJtxtFile = "" Then LISTAPRJtxtFile = "PRJ_List.txt"

'If CADDIR = "" Then CADDIR = "File_CAD"

'TMPfile = Half_Path & "Temp\Currentfile.jpg"
'Debug.Print TMPfile
VariablesEnvironnementFindTMP2 = Half_Path & "\Temp\Currentfile.jpg"
End Function


Sub Toexcel0()

Dim Excel As Object
Dim workbooks As workbooks
Dim workbook As workbook
Dim Sheets As Object
Dim Sheet As Object
Dim worksheet As Excel.worksheet
Dim myworkbook As Excel.workbook
Dim myworksheet As Excel.worksheet
TMPfile = Half_Path & "\Temp\Currentfile" & Counter & ".jpg"


'If TMPExcel = "" Then TMPExcel = "C:\Users\rbartola\AppData\Local\Temp\BOM" ' to remove
'If TMPExcel = "" Then TMPExcel = "C:\Users\rbartola\AppData\Local\Temp\BOM" ' to remove

'On Error Resume Next
'Set Excel = GetObject(, "EXCEL.Application")
'If Err.Number <> 0 Then
'Err.Clear
'Set Excel = CreateObject("EXCEL.Application")
'Else
'Err.Clear
'MsgBox "Please note you have to close Excel", vbCritical
'Exit Sub
'End If
Set Excel = CreateObject("EXCEL.Application")
'Excel.Visible = True
Excel.Visible = False
'load a sheet
Set workbooks = Excel.Application.workbooks
Set myworkbook = Excel.workbooks.Add
'Set myworksheet = Excel.ActiveWorkbook.Add("BOM")
'Set myworksheet = Excel.Sheets() '.Add()
Set myworksheet = Excel.Sheets.Add()
myworksheet.Name = "BOM"


'download the properties
'row one
Excel.Cells(1, 1) = "Part Number"
Excel.Cells(1, 2) = "Thickness"
Excel.Cells(1, 3) = "Material"
Excel.Cells(1, 4) = "Mass"
Excel.Cells(1, 5) = "Image"
Excel.Cells(1, 6) = "Username"
Excel.Cells(2, 6) = Excel.UserName
Excel.Columns("E").ColumnWidth = 23
RowIndex = 1
Excel.ActiveCell.Offset(0, 4).Select
'Excel.Cells.Offset(0, 4).Select
'Excel.ActiveWorkbook.SaveAs "C:\Users\rbartola\AppData\Local\Temp\BOM.Excel"
Excel.ActiveWorkbook.SaveAs TMPExcel
Excel.ActiveWorkbook.Close savechanges:=True
'Excel.ActiveWorkbook.Close (1)
'Excel.Visible = True
Excel.Visible = False
'Counter = Counter + 1
End Sub

Sub Toexcel2()

Dim Excel As Object
Dim workbooks As workbooks
Dim workbook As workbook
Dim Sheets As Object
Dim Sheet As Object
Dim worksheet As Excel.worksheet
Dim myworkbook As Excel.workbook
Dim myworksheet As Excel.worksheet
Dim MyCell As Range


Set Excel = CreateObject("EXCEL.Application")
TMPfile = Half_Path & "\Temp\Currentfile" & Counter & ".jpg"
'If TMPExcel = "" Then TMPExcel = "C:\Users\rbartola\AppData\Local\Temp\BOM" ' to remove
Excel.workbooks.Open TMPExcel
'Excel.Visible = True
Excel.Visible = False

'If RowIndex = "" Then RowIndex = 1
'load a sheet
Set workbooks = Excel.Application.workbooks
'workbook().Worksheets().Activate
'Set myworkbook = Excel.workbooks '.Add
'Set myworksheet = Excel.ActiveWorkbook() '.Add
'Set myworksheet = Excel.Sheets("BOM").Activate '.Add
'RB-'Debug.Print "RowIndex = " & RowIndex

'download the properties
'row one
'RowIndex1 = Excel.ActiveCell.Row
'Excel.Rows(RowIndex).RowHeight = 62
'Next i
Excel.ActiveCell.Offset(1, 0).Select
Excel.ActiveCell.Offset(0, -4).Select
Excel.ActiveCell.Value = NameOfThePart
Excel.ActiveCell.Offset(0, 4).Select
RowIndex1 = Excel.ActiveCell.Row
Excel.Rows(RowIndex1).RowHeight = 62

Excel.ActiveSheet.Pictures.Insert(TMPfile).Select 'Path to where pictures are stored
With Excel.Selection 'to readd
'.Left = ActiveCell.Left
'.Top = ActiveCell.Top
.ShapeRange.LockAspectRatio = msoFalse
'.ShapeRange.LockAspectRatio = msoTrue
.ShapeRange.Height = 60#
.ShapeRange.Width = 45#
.ShapeRange.Rotation = 0#
End With


Excel.ActiveWorkbook.Close savechanges:=True
'Excel.ActiveWorkbook.Close (1) 'True
'Excel.Visible = False
Counter = Counter + 1
End Sub


Sub AnalyseSubProductForImage(oStiDBItem, FatherName As String, TabStrFather As String)

'''OOOK-----------------------------------------------------------------FUNZIONA !!!!!!! Grande !!!!!!!!!!!!!!!!!!!!!
'''OOOK-----------------------------------------------------------------FUNZIONA !!!!!!! Grande !!!!!!!!!!!!!!!!!!!!!
    Dim i As Integer
    Dim oStiDBChildren
    Dim oStiDBItem2 ' As StiDBItem  -- Smarteam is not SetUp , API recognize , so use AnyObject Type
    Dim SonName As String
    Dim TabStrChildren As String
   
    Set oStiDBChildren = oStiDBItem.GetChildren
    For i = 1 To oStiDBChildren.Count
        Set oStiDBItem2 = oStiDBChildren.Item(i)
'        SonName = oStiDBItem2.GetDocumentFullPath
        'SonNameSolo = EstraiFile(SonName) ' oStiDBItem2.Name ' come si da il nome da solo? 'DocumentoAttuale = CATIA.ActiveDocument.Name
        TabStrChildren = TabStrFather & "-"
        LinkType = CStr(oStiDBChildren.LinkType(i))
        
        CATIA.ActiveDocument oStiDBItem2.GetDocumentFullPath
        Call ReadImage
       
           Call AnalyseSubProductForImage(oStiDBItem2, FatherName, TabStrChildren)
    Next i

End Sub


Function EstraiDirectory(Percorso)
'============================================================================================================================================
'********************************************************************************************************************************************
'
' Function: Extracts dir name from fullname
' Version: 000 del 08/06/2015
' Author: Roberto Bartola robertobartola@gmail.com
'
'********************************************************************************************************************************************
'============================================================================================================================================
EstraiDirectory = Left(Percorso, Len(Percorso) - Len(Right(Percorso, Len(Percorso) - InStrRev(Percorso, "\"))) - 1)
End Function

Function EstraiFile(Percorso)
'============================================================================================================================================
'********************************************************************************************************************************************
'
' Function: Extracts the filename from fullname
' Version: 000 del 08/06/2015
' Author: Roberto Bartola robertobartola@gmail.com
'
'********************************************************************************************************************************************
'============================================================================================================================================
EstraiFile = Right(Percorso, Len(Percorso) - InStrRev(Percorso, "\"))
End Function

Attribute VB_Name = "Link_Analyze"
Sub AnalyseLink()
    Dim oStiEngine ' As StiEngine
    Set oStiEngine = CATIA.GetItem("CAIEngine")
    Dim oStiDBItem ' As StiDBItem
    Set oStiDBItem = oStiEngine.GetStiDBItemFromAnyObject(CATIA.ActiveDocument)
    
    'RB-'Debug.Print CATIA.ActiveDocument.FullName ''Output
    Call ReadImage
    Call AnalyseSubProduct(oStiDBItem, CATIA.ActiveDocument.FullName, "")
End Sub

Sub AnalyseSubProduct(oStiDBItem, FatherName As String, TabStrFather As String)
    Dim i As Integer
    Dim oStiDBChildren
    Dim oStiDBItem2 ' As StiDBItem  -- Smarteam is not SetUp , API recognize , so use AnyObject Type
    Dim SonName As String
    Dim TabStrChildren As String
   
    Set oStiDBChildren = oStiDBItem.GetChildren
    For i = 1 To oStiDBChildren.Count
        Set oStiDBItem2 = oStiDBChildren.Item(i)
        SonName = oStiDBItem2.GetDocumentFullPath
        SonNameSolo = EstraiFile(SonName) ' oStiDBItem2.Name ' come si da il nome da solo? 'DocumentoAttuale = CATIA.ActiveDocument.Name
        TabStrChildren = TabStrFather & "-"
        LinkType = CStr(oStiDBChildren.LinkType(i))
    'RB-'Debug.Print "Nome Figlio " & SonName & "Nome Padre " & FatherName
'    Set documents1 = CATIA.Documents
'Set Document1 = documents1.Open(Filename)

CATIA.Documents.Open (SonName)
    NameOfThePart = SonName
    Call ReadImage
    Call Toexcel2
    CATIA.ActiveDocument.Close
        
    
    FatherName = SonName
    ' Call Toexcel2
           Call AnalyseSubProduct(oStiDBItem2, FatherName, TabStrChildren)
    Next i

End Sub

Attribute VB_Name = "Start"
Public TMPfile As String
Public RowIndex
Public TMPExcel As String
Public Counter As Integer
Public Half_Path
Public NameOfThePart As String


Sub CatMain()
Dim Excel As Object
Set Excel = CreateObject("EXCEL.Application")
Dim strEnviron As String
Dim Indx As Integer
Dim pos As Integer
'Dim TMPfile As String
'Dim TMPExcel As String
RowIndex = 1
Indx = 1
Counter = 0

' Enviroenment
strEnviron = Environ(Indx)
Do While strEnviron <> ""
pos = InStr(1, strEnviron, "=")
Find_Variable = Left(strEnviron, pos - 1)
Find_Value = Right(strEnviron, Len(strEnviron) - pos)

'search all the variables
If Find_Variable = "LOCALAPPDATA" Then Half_Path = Find_Value

Indx = Indx + 1
strEnviron = Environ(Indx)
Loop
'Debug.Print TMPfile
TMPfile = Half_Path & "\Temp\Currentfile" & Counter & ".jpg"
TMPExcel = Half_Path & "\Temp\BOM"
'Debug.Print Counter & " " & TMPExcel
' End Enviroenment

'initialize excel
Call Toexcel0

'kore
filadalavorare = EstraiFile(CATIA.ActiveDocument.FullName)
FileDaRiaprireAllaFine = CATIA.ActiveDocument.FullName
CATIA.DisplayFileAlerts = False
Call AnalyseLink
CATIA.Documents.Open (FileDaRiaprireAllaFine)
CATIA.DisplayFileAlerts = True
'end kore


'to fix

'Call AnalyseLinkToImage
'Debug.Print "Here it comes"
Excel.workbooks.Open TMPExcel
Excel.Visible = True
'Excel.Columns("A").ColumnWidth = 23
'Excel.ActiveSheet ("BOM")
Excel.Worksheets("BOM").Range("A:D").EntireColumn.AutoFit

End Sub

Attribute VB_Name = "TopDownOpenFiles"
'Sub CatMain() ' Main Sub
'filadalavorare = EstraiFile(CATIA.ActiveDocument.FullName)
'FileDaRiaprireAllaFine = CATIA.ActiveDocument.FullName
''replace Lista_Bottom_up con Lista_TOP_DOWN - fatto
'' aggiungi File_analizzato_name ad ogni Lista_TOP_DOWN
'
'CATIA.DisplayFileAlerts = False
'
''If WouldBE_DEBUG.Visible = False Then WouldBE_DEBUG.Show vbModeless
''Call Dir_current_RB_go_drw ' da creare, copio il...go e attivo solo il drw
'Call AnalyseLink
'
''Call Check_topdown_loop
'
'CATIA.Documents.Open (FileDaRiaprireAllaFine)
'CATIA.DisplayFileAlerts = True
'
'
'End Sub

Sub Check_topdown_loop()
LocaldirectoryRB = LocalDir & "\" & CADDIR

  For r = 0 To WouldBe_Debug.CheckFigli1.ListCount - 1
DocFullName_RB = LocaldirectoryRB & "\" & WouldBe_Debug.CheckFigli1.List(r)
'MsgBox DocFullName_RB
'CATIA.Documents.Open DocFullName_RB
CATIA.Documents.Open (DocFullName_RB)
Call AnalyseLink
CATIA.ActiveDocument.Close


End Sub
