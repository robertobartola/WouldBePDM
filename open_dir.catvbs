Language="VBSCRIPT"
' Macro created by Roberto Bartola on 2013/2014

Set Document = CATIA.ActiveDocument
DocPath = Document.Path
cmd="C:\Windows\explorer.exe "&DocPath

Sub CATMain()
If CATIA.Documents.Count >0 Then
  call CATIA.SystemService.ExecuteBackgroundProcessus (cmd)
Else
MsgBox "This tool needs a CATIA file"
End If
End Sub
