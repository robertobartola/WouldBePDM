'Language="VBSCRIPT"
' Macro created by Diego Sammarco on 2013/2014

Dim AllDocs
Dim Document1
Dim DocFullName1
Dim t

Set Document = CATIA.ActiveDocument
DocFullName = Document.FullName
Argument = Chr(34)&DocFullName&Chr(34)

Sub CATMain()
If CATIA.Documents.Count >0 Then

					Dim strNomeFile
					FileString = "zztmppdt.txt"
					Set StatusShell = CreateObject("WScript.Shell")
					Set objExec = StatusShell.Exec ("%comspec% /c echo %TEMP%")
					PathString = objExec.StdOut.Readline
					strNomeFile = PathString&"\"&FileString

Set Datos = CATIA.FileSystem.CreateFile(strNomeFile , True)
Set ostream = Datos.OpenAsTextStream("ForAppending")

Exe = MsgBox("This CATScript will close all files in the session without saving them"  & Chr(10) & "And will update from svn the file:" & Chr(10) & DocFullName & Chr(10) & "Would you like to continue?", vbOKCancel, "UPDATE Active Document and CLOSE ALL DOCUMENTS")
	If Exe = vbOK Then

		Set wshShell = CreateObject("WScript.Shell")
		wshShell.run "%comspec% /c TortoiseProc.exe /command:update /path:"&Argument,0,true

			      AllDocs = CATIA.Documents.Count
			    If AllDocs > 0 Then
			        For Each CATIA_Document In CATIA.Documents 
					CATIA_Document.Activate
					Set Document1 = CATIA.ActiveDocument
					DocFullName1 = Document1.FullName

' APPENDE DocFullName1 NEL FILE DI TESTO 

					ostream.Write  DocFullName1 & Chr(10)
			        Next

			    End If

' CHIUDE IL FILE DI TESTO

				ostream.Close

' CHIUDE TUTTI I DOCUMENTI

		Set windowsopen = CATIA.Windows
			for i = 1 to windowsopen.count
				CATIA.ActiveDocument.Close
			next

'RIAPRE OGNI DOCUMENTO LISTATO NEL FILE DI TESTO

		Set oreading = Datos.OpenAsTextStream("ForReading")
		
		While Not oreading.AtEndOfStream
			DocToOpen = oreading.ReadLine
				If DocToOpen <>"" Then
			       CATIA.Documents.Open (DocToOpen)
				End If
		Wend
		oreading.Close

	End If


' CANCELLA IL FILE DI TESTO

		Set wshShell1 = CreateObject("WScript.Shell")
		wshShell1.run "%comspec% /c del /F /Q "&strNomeFile,2,true

Else
MsgBox "This tool needs a CATIA file"
End If

End Sub
