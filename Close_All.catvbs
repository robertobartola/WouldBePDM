Sub CATMain()
If CATIA.Documents.Count >0 Then

' Macro created by Diego Sammarco on 2013/2014

Exe = MsgBox("Close all files in the session without saving them?", vbOKCancel, "CLOSE ALL DOCUMENTS")
	If Exe = vbOK Then

        For Each CATIA_Document In CATIA.Documents 
              CATIA_Document.Close
        Next
	End if

Else
MsgBox "This tool needs a CATIA file"
End If

End Sub
